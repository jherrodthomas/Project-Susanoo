// HazardTrackingSystem — generated by tools/gen_safety_docs.py from safety/mil-std-882e/catalog.yaml.
// Do not edit by hand: change the catalog and regenerate.
// Status: planning view only; not evidence of completed analysis or verification.

package HazardTrackingSystem {
    private import ScalarValues::*;
    private import SusanooLibrary::*;
    private import SusanooArchitecture::*;
    part def HazardLog {
        attribute configurationId : String;
        ref item records : Hazard[0..*];
    }

    attribute def ChangeReopens;
    attribute def ClosureCriteriaMet;
    attribute def DecisionRecordLinked;
    attribute def EvidenceLinked;
    attribute def MitigationLinked;
    state def HazardRecordStatus {
        entry; then Open;
        state Open;
        state Mitigated;
        state Verified;
        state Accepted;
        state Closed;
        transition t1 first Open accept MitigationLinked then Mitigated;
        transition t2 first Mitigated accept EvidenceLinked then Verified;
        transition t3 first Verified accept DecisionRecordLinked then Accepted;
        transition t4 first Accepted accept ClosureCriteriaMet then Closed;
        transition t5 first Accepted accept ChangeReopens then Open;
    }
}
