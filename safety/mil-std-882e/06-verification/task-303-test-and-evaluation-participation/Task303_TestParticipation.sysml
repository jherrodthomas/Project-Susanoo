// Task303_TestParticipation — generated by tools/gen_safety_docs.py from safety/mil-std-882e/catalog.yaml.
// Do not edit by hand: change the catalog and regenerate.
// Status: planning view only; not evidence of completed analysis or verification.

package Task303_TestParticipation {
    private import ScalarValues::*;
    private import SusanooLibrary::*;
    private import SusanooArchitecture::*;
    attribute def AnomalyDispositioned;
    attribute def IndependentReviewApproves;
    attribute def StopCondition;
    attribute def TestComplete;
    attribute def TestHazardAnalysisComplete;
    state def TestSafetyRelease {
        entry; then Planned;
        state Planned;
        state HazardsReviewed;
        state Released { doc /* authorized for stated configuration */ }
        state Executed;
        state Suspended { doc /* stop-test condition */ }
        transition t1 first Planned accept TestHazardAnalysisComplete then HazardsReviewed;
        transition t2 first HazardsReviewed accept IndependentReviewApproves then Released;
        transition t3 first Released accept TestComplete then Executed;
        transition t4 first Released accept StopCondition then Suspended;
        transition t5 first Suspended accept AnomalyDispositioned then HazardsReviewed;
    }
}
