// Task402_Applicability — generated by tools/gen_safety_docs.py from safety/mil-std-882e/catalog.yaml.
// Do not edit by hand: change the catalog and regenerate.
// Status: planning view only; not evidence of completed analysis or verification.

package Task402_Applicability {
    private import ScalarValues::*;
    private import SusanooLibrary::*;
    private import SusanooArchitecture::*;
    attribute def AcceptedIntoBaseline;
    attribute def EnergeticItemProposed;
    attribute def Rejected;
    state def Task402Applicability {
        entry; then NotApplicable;
        state NotApplicable;
        state UnderReview;
        state Applicable;
        transition t1 first NotApplicable accept EnergeticItemProposed then UnderReview;
        transition t2 first UnderReview accept Rejected then NotApplicable;
        transition t3 first UnderReview accept AcceptedIntoBaseline then Applicable;
    }
}
