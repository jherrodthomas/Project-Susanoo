// Task401_SafetyVerification — generated by tools/gen_safety_docs.py from safety/mil-std-882e/catalog.yaml.
// Do not edit by hand: change the catalog and regenerate.
// Status: planning view only; not evidence of completed analysis or verification.

package Task401_SafetyVerification {
    private import ScalarValues::*;
    private import SusanooLibrary::*;
    private import SusanooArchitecture::*;
    private import SusanooRequirements::*;
    // Requirement records shown here are owned by models/sysml/model/Requirements.sysml (generated from requirements/); satisfy relations by Satisfaction.sysml.
    view requirementsInScope {
        expose SusanooRequirements::'SYS-001';
        expose SusanooRequirements::'SYS-002';
        expose SusanooRequirements::'SYS-003';
    }
    verification def <'VER-001'> Ver001 {
        objective {
            verify SusanooRequirements::'SYS-001';
        }
    }
    verification def <'VER-002'> Ver002 {
        objective {
            verify SusanooRequirements::'SYS-002';
        }
    }
    verification def <'VER-003'> Ver003 {
        objective {
            verify SusanooRequirements::'SYS-003';
        }
    }
}
