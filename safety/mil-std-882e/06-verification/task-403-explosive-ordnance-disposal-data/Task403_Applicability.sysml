// Task403_Applicability — generated by tools/gen_safety_docs.py from safety/mil-std-882e/catalog.yaml.
// Do not edit by hand: change the catalog and regenerate.
// Status: planning view only; not evidence of completed analysis or verification.

package Task403_Applicability {
    private import ScalarValues::*;
    private import SusanooLibrary::*;
    private import SusanooArchitecture::*;
    attribute def OrdnanceProposed;
    attribute def ProposalRejected;
    state def Task403Applicability {
        entry; then NotApplicable;
        state NotApplicable;
        state Escalated { doc /* outside charter */ }
        transition t1 first NotApplicable accept OrdnanceProposed then Escalated;
        transition t2 first Escalated accept ProposalRejected then NotApplicable;
    }
}
