// SafetyVerification — generated by tools/gen_safety_docs.py from safety/mil-std-882e/catalog.yaml.
// Do not edit by hand: change the catalog and regenerate.
// Status: planning view only; not evidence of completed analysis or verification.

package SafetyVerification {
    private import ScalarValues::*;
    private import SusanooLibrary::*;
    private import SusanooArchitecture::*;
    action def VerifyRiskReduction {
        action planVerification { doc /* Select method per requirement */ }
        action confirmTestSafety { doc /* Confirm test hazards controlled */ }
        action execute { doc /* Execute analysis, test or demonstration */ }
        action recordEvidence { doc /* Record evidence with provenance and hash */ }
        action assessEffectiveness { doc /* Assess mitigation effectiveness */ }
        first start then planVerification;
        first planVerification then confirmTestSafety;
        first confirmTestSafety then execute;
        first execute then recordEvidence;
        first recordEvidence then assessEffectiveness;
        first assessEffectiveness then done;
        // iteration: assessEffectiveness -> planVerification when failed or inconclusive (informal; merge node omitted)
    }
}
