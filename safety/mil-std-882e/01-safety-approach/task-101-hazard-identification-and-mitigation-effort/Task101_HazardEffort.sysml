// Task101_HazardEffort — generated by tools/gen_safety_docs.py from safety/mil-std-882e/catalog.yaml.
// Do not edit by hand: change the catalog and regenerate.
// Status: planning view only; not evidence of completed analysis or verification.

package Task101_HazardEffort {
    private import ScalarValues::*;
    private import SusanooLibrary::*;
    private import SusanooArchitecture::*;
    action def HazardIdentificationAndMitigationEffort {
        action defineScope { doc /* Confirm configuration and boundary */ }
        action identify { doc /* Identify hazards per selected tasks */ }
        action assess { doc /* Assess initial risk */ }
        action mitigate { doc /* Allocate mitigations and requirements */ }
        action verifyEffectiveness { doc /* Verify mitigation effectiveness */ }
        action report { doc /* Report status and request decisions */ }
        first start then defineScope;
        first defineScope then identify;
        first identify then assess;
        first assess then mitigate;
        first mitigate then verifyEffectiveness;
        first verifyEffectiveness then report;
        first report then done;
        // iteration: report -> identify when design or CONOPS change (informal; merge node omitted)
    }
}
