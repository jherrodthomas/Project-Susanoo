// Task104_Reviews — generated by tools/gen_safety_docs.py from safety/mil-std-882e/catalog.yaml.
// Do not edit by hand: change the catalog and regenerate.
// Status: planning view only; not evidence of completed analysis or verification.

package Task104_Reviews {
    private import ScalarValues::*;
    private import SusanooLibrary::*;
    private import SusanooArchitecture::*;
    action def ReviewAndAudit {
        action confirmApplicability { doc /* Confirm task is applicable */ }
        action preparePackage { doc /* Prepare configuration-specific evidence package */ }
        action conductReview { doc /* Conduct review or audit */ }
        action trackActions { doc /* Track findings to closure */ }
        first start then confirmApplicability;
        first confirmApplicability then preparePackage;
        first preparePackage then conductReview;
        first conductReview then trackActions;
        first trackActions then done;
    }
}
