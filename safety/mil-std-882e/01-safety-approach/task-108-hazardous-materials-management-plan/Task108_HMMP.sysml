// Task108_HMMP — generated by tools/gen_safety_docs.py from safety/mil-std-882e/catalog.yaml.
// Do not edit by hand: change the catalog and regenerate.
// Status: planning view only; not evidence of completed analysis or verification.

package Task108_HMMP {
    private import ScalarValues::*;
    private import SusanooLibrary::*;
    private import SusanooArchitecture::*;
    part def HazMatInventory {
        ref item entries : HazMatEntry[0..*];
    }
    item def HazMatEntry {
        attribute material : String;
        attribute location : String;
        attribute quantity : Real;
        attribute sdsRef : String;
        attribute disposal : String;
    }
    enum def MaterialClass {
        enum Fuel;
        enum HydraulicFluid;
        enum LithiumIonCell;
        enum Coolant;
        enum Lubricant;
    }
}
