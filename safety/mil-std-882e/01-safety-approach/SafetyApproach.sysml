// SafetyApproach — generated by tools/gen_safety_docs.py from safety/mil-std-882e/catalog.yaml.
// Do not edit by hand: change the catalog and regenerate.
// Status: planning view only; not evidence of completed analysis or verification.

package SafetyApproach {
    private import ScalarValues::*;
    private import SusanooLibrary::*;
    private import SusanooArchitecture::*;
    part def SafetyProgram {
        doc /* Plans and agreements that document the SUS-I1 safety approach. */
        attribute configurationId : String;
        attribute standardEdition : String;
        ref item sspp : SystemSafetyProgramPlan[1];
        ref item hmp : HazardManagementPlan[1];
        ref item hmmp : HazMatManagementPlan[0..1];
        part ipt : SafetyIPT[1];
    }
    item def SystemSafetyProgramPlan {
        attribute revision : String;
        attribute approvalRecord : String;
    }
    item def HazardManagementPlan {
        attribute riskMatrixRef : String;
        attribute closureCriteria : String;
    }
    item def HazMatManagementPlan {
        attribute inventoryRef : String;
    }
    part def SafetyIPT {
        attribute charter : String;
    }
}
