// Task105_IPT — generated by tools/gen_safety_docs.py from safety/mil-std-882e/catalog.yaml.
// Do not edit by hand: change the catalog and regenerate.
// Status: planning view only; not evidence of completed analysis or verification.

package Task105_IPT {
    private import ScalarValues::*;
    private import SusanooLibrary::*;
    private import SusanooArchitecture::*;
    part def SafetyIPT {
        part safetyLead : Role[1];
        part systemsLead : Role[1];
        part softwareSafetyLead : Role[1];
        part humanFactorsLead : Role[1];
        part testLead : Role[1];
    }
    part def Role {
        attribute name : String;
        attribute authority : String;
        attribute independent : Boolean;
    }
}
