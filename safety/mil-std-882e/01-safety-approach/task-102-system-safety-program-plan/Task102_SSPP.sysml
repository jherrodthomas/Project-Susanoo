// Task102_SSPP — generated by tools/gen_safety_docs.py from safety/mil-std-882e/catalog.yaml.
// Do not edit by hand: change the catalog and regenerate.
// Status: planning view only; not evidence of completed analysis or verification.

package Task102_SSPP {
    private import ScalarValues::*;
    private import SusanooLibrary::*;
    private import SusanooArchitecture::*;
    requirement def <'SSPP-001'> DefineRiskAuthority {
        doc /* SSPP shall name the risk acceptance authority for each risk level */
    }
    requirement sspp_001 : DefineRiskAuthority;
    requirement def <'SSPP-002'> DefineTaskSelection {
        doc /* SSPP shall record selected and tailored tasks with rationale */
    }
    requirement sspp_002 : DefineTaskSelection;
    requirement def <'SSPP-003'> SeparateRiskScales {
        doc /* SSPP shall keep 882E risk and ARP4761A failure-condition scales distinct */
    }
    requirement sspp_003 : SeparateRiskScales;
    requirement def <'SSPP-004'> DefineSoftwareApproach {
        doc /* SSPP shall define the software contribution to system risk approach */
    }
    requirement sspp_004 : DefineSoftwareApproach;
    verification def <'SSPP-REVIEW'> SsppReview {
        objective {
            verify sspp_001;
            verify sspp_002;
            verify sspp_003;
            verify sspp_004;
        }
    }
}
