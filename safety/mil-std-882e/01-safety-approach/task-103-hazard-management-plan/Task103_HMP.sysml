// Task103_HMP — generated by tools/gen_safety_docs.py from safety/mil-std-882e/catalog.yaml.
// Do not edit by hand: change the catalog and regenerate.
// Status: planning view only; not evidence of completed analysis or verification.

package Task103_HMP {
    private import ScalarValues::*;
    private import SusanooLibrary::*;
    private import SusanooArchitecture::*;
    attribute def AcceptanceRequested;
    attribute def AuthorityApproves;
    attribute def AuthorityRejects;
    attribute def ChangeOrMishap;
    attribute def EvidenceAccepted;
    attribute def Fielded;
    attribute def HazardEliminatedOrRetired;
    attribute def MitigationRecorded;
    attribute def VerificationFailed;
    state def HazardLifecycle {
        doc /* Status transitions governed by the HMP; values follow SusanooLibrary::HazardStatus. */
        entry; then Open;
        state Open { doc /* identified and recorded */ }
        state Mitigated { doc /* controls allocated and implemented */ }
        state Verified { doc /* effectiveness evidenced */ }
        state PendingAcceptance { doc /* residual risk awaiting decision */ }
        state Accepted { doc /* authorized decision recorded */ }
        state Closed;
        state Monitor { doc /* tracked in service */ }
        transition t1 first Open accept MitigationRecorded then Mitigated;
        transition t2 first Mitigated accept EvidenceAccepted then Verified;
        transition t3 first Verified accept VerificationFailed then Mitigated;
        transition t4 first Verified accept AcceptanceRequested then PendingAcceptance;
        transition t5 first PendingAcceptance accept AuthorityApproves then Accepted;
        transition t6 first PendingAcceptance accept AuthorityRejects then Mitigated;
        transition t7 first Accepted accept Fielded then Monitor;
        transition t8 first Monitor accept ChangeOrMishap then Open;
        transition t9 first Accepted accept HazardEliminatedOrRetired then Closed;
    }
}
