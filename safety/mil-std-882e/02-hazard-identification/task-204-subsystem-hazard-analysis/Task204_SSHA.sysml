// Task204_SSHA — generated by tools/gen_safety_docs.py from safety/mil-std-882e/catalog.yaml.
// Do not edit by hand: change the catalog and regenerate.
// Status: planning view only; not evidence of completed analysis or verification.

package Task204_SSHA {
    private import ScalarValues::*;
    private import SusanooLibrary::*;
    private import SusanooArchitecture::*;
    part def SubsystemHazardAnalysis {
        attribute subsystemId : String;
        attribute designRevision : String;
        ref item failureModes : FailureModeEntry[0..*];
    }
    item def FailureModeEntry {
        attribute failureMode : String;
        attribute localEffect : String;
        attribute systemEffect : String;
        attribute detection : String;
        attribute hazardId : String;
        attribute softwareContribution : Boolean;
    }
}
