// HazardAnalyses — generated by tools/gen_safety_docs.py from safety/mil-std-882e/catalog.yaml.
// Do not edit by hand: change the catalog and regenerate.
// Status: planning view only; not evidence of completed analysis or verification.

package HazardAnalyses {
    private import ScalarValues::*;
    private import SusanooLibrary::*;
    private import SusanooArchitecture::*;
    action def HazardAnalysisRelationships {
        action phl { doc /* Task 201 PHL */ }
        action pha { doc /* Task 202 PHA */ }
        action fha { doc /* Task 208 FHA */ }
        action srha { doc /* Task 203 SRHA */ }
        action ssha { doc /* Task 204 SSHA */ }
        action sha { doc /* Task 205 SHA */ }
        action osha { doc /* Task 206 O&SHA */ }
        first start then phl;
        first phl then pha;
        first pha then fha;
        first fha then srha;
        first srha then ssha;
        first ssha then sha;
        first sha then osha;
        first osha then done;
        // iteration: sha -> ssha when interface cause found (informal; merge node omitted)
        // iteration: osha -> pha when new operating scenario (informal; merge node omitted)
    }
}
