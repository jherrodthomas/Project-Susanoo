// Task208_FHA — generated by tools/gen_safety_docs.py from safety/mil-std-882e/catalog.yaml.
// Do not edit by hand: change the catalog and regenerate.
// Status: planning view only; not evidence of completed analysis or verification.

package Task208_FHA {
    private import ScalarValues::*;
    private import SusanooLibrary::*;
    private import SusanooArchitecture::*;
    action def WalkerFunctionalChain {
        action senseIntent { doc /* Sense pilot intent */ }
        action estimateState { doc /* Estimate walker state */ }
        action planMotion { doc /* Plan motion and balance */ }
        action actuateJoints { doc /* Actuate joints */ }
        action monitorSafety { doc /* Monitor and enforce protective stop */ }
        first start then senseIntent;
        first senseIntent then estimateState;
        first estimateState then planMotion;
        first planMotion then actuateJoints;
        first actuateJoints then monitorSafety;
        first monitorSafety then done;
        // iteration: monitorSafety -> actuateJoints when inhibit on fault (informal; merge node omitted)
    }

    item def FunctionalFailure {
        attribute functionId : String;
        attribute failureType : FunctionalFailureType;
        attribute hazardId : String;
        attribute swci : SoftwareControlCategory;
    }
    enum def FunctionalFailureType {
        enum Loss;
        enum Erroneous;
        enum Untimely;
        enum Unintended;
        enum Degraded;
    }
}
