// Task201_PHL — generated by tools/gen_safety_docs.py from safety/mil-std-882e/catalog.yaml.
// Do not edit by hand: change the catalog and regenerate.
// Status: planning view only; not evidence of completed analysis or verification.

package Task201_PHL {
    private import ScalarValues::*;
    private import SusanooLibrary::*;
    private import SusanooArchitecture::*;
    part def PreliminaryHazardList {
        attribute configurationId : String;
        attribute revision : String;
        ref item entries : PHLEntry[0..*];
    }
    item def PHLEntry {
        attribute hazardId : String;
        attribute hazardSource : String;
        attribute missionPhase : String;
        attribute potentialMishap : String;
    }
}
