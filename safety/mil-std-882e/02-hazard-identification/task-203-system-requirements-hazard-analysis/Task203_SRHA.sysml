// Task203_SRHA — generated by tools/gen_safety_docs.py from safety/mil-std-882e/catalog.yaml.
// Do not edit by hand: change the catalog and regenerate.
// Status: planning view only; not evidence of completed analysis or verification.

package Task203_SRHA {
    private import ScalarValues::*;
    private import SusanooLibrary::*;
    private import SusanooArchitecture::*;
    private import RequirementDerivation::*;
    private import SusanooRequirements::*;
    // Requirement records shown here are owned by models/sysml/model/Requirements.sysml (generated from requirements/); satisfy relations by Satisfaction.sysml.
    view requirementsInScope {
        expose SusanooRequirements::'SYS-001';
        expose SusanooRequirements::'SYS-002';
        expose SusanooRequirements::'SYS-003';
        expose SusanooRequirements::'SYS-004';
        expose SusanooRequirements::'SYS-005';
        expose SusanooRequirements::'SYS-006';
        expose SusanooRequirements::'SYS-007';
        expose SusanooRequirements::'SYS-008';
        expose SusanooRequirements::'SYS-009';
        expose SusanooRequirements::'SYS-010';
        expose SusanooRequirements::'SYS-011';
        expose SusanooRequirements::'SYS-012';
        expose SusanooRequirements::'SYS-013';
        expose SusanooRequirements::'SYS-014';
        expose SusanooRequirements::'SYS-015';
        expose SusanooRequirements::'SYS-016';
        expose SusanooRequirements::'SYS-017';
        expose SusanooRequirements::'SYS-018';
        expose SusanooRequirements::'SYS-019';
        expose SusanooRequirements::'SYS-020';
        expose SusanooRequirements::'SYS-021';
        expose SusanooRequirements::'SYS-022';
        expose SusanooRequirements::'SYS-023';
        expose SusanooRequirements::'SYS-024';
    }
    #derivation connection { end #original ::> SusanooRequirements::'SYS-002'; end #derive ::> SusanooRequirements::'SYS-010'; }
    #derivation connection { end #original ::> SusanooRequirements::'SYS-002'; end #derive ::> SusanooRequirements::'SYS-011'; }
    #derivation connection { end #original ::> SusanooRequirements::'SYS-003'; end #derive ::> SusanooRequirements::'SYS-012'; }
}
