// Task205_SHA — generated by tools/gen_safety_docs.py from safety/mil-std-882e/catalog.yaml.
// Do not edit by hand: change the catalog and regenerate.
// Status: planning view only; not evidence of completed analysis or verification.

package Task205_SHA {
    private import ScalarValues::*;
    private import SusanooLibrary::*;
    private import SusanooArchitecture::*;
    part def SHAInterfaceContext {
        part pwr : PowerSystem;
        part ctl : MotionControl;
        part saf : SafetyMonitor;
        part dck : UavDock;
        part uav : ObservationUav;
        connection c1 connect saf to ctl { doc /* torque inhibit */ }
        connection c2 connect saf to pwr { doc /* energy isolation */ }
        connection c3 connect pwr to ctl { doc /* drive power */ }
        connection c4 connect dck to uav { doc /* retention, charge, rotor inhibit */ }
        connection c5 connect pwr to dck { doc /* dock supply */ }
    }
}
