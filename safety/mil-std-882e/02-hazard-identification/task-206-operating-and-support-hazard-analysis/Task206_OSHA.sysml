// Task206_OSHA — generated by tools/gen_safety_docs.py from safety/mil-std-882e/catalog.yaml.
// Do not edit by hand: change the catalog and regenerate.
// Status: planning view only; not evidence of completed analysis or verification.

package Task206_OSHA {
    private import ScalarValues::*;
    private import SusanooLibrary::*;
    private import SusanooArchitecture::*;
    private import ConceptOperations::*;
    // Analysed modes are owned by concept/ConceptOperations.sysml (single source of truth); not redefined here.
    state modesUnderAnalysis : ConceptOperations::OperatingModes {
        doc /* O&SHA scope - every CONOPS mode and transition, including ingress/egress, maintenance and UAV launch/recovery. */
    }

    item def OSHARow {
        doc /* One row per mode, transition or task step analysed. */
        attribute modeId : String;
        attribute transitionId : String;
        attribute taskStep : String;
        attribute personnel : String;
        attribute hazardId : String;
        attribute procedureControl : String;
        attribute residualRisk : RiskAssessment;
    }
}
