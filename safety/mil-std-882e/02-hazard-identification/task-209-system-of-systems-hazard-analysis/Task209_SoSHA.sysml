// Task209_SoSHA — generated by tools/gen_safety_docs.py from safety/mil-std-882e/catalog.yaml.
// Do not edit by hand: change the catalog and regenerate.
// Status: planning view only; not evidence of completed analysis or verification.

package Task209_SoSHA {
    private import ScalarValues::*;
    private import SusanooLibrary::*;
    private import SusanooArchitecture::*;
    part def GnssConstellation;
    part def AirspaceUsers;
    part def SiteInfrastructureSystem;
    part def SiteVehicles;
    part def SoSContext {
        part sus : IntegratedSystem;
        part gnss : GnssConstellation;
        part airspace : AirspaceUsers;
        part site : SiteInfrastructureSystem;
        part vehicles : SiteVehicles;
        connection c1 connect gnss to sus { doc /* navigation signals */ }
        connection c2 connect airspace to sus { doc /* deconfliction */ }
        connection c3 connect site to sus { doc /* power, fuel, comms */ }
        connection c4 connect vehicles to sus { doc /* shared workspace */ }
    }
}
