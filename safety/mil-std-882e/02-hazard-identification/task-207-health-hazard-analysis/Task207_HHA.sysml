// Task207_HHA — generated by tools/gen_safety_docs.py from safety/mil-std-882e/catalog.yaml.
// Do not edit by hand: change the catalog and regenerate.
// Status: planning view only; not evidence of completed analysis or verification.

package Task207_HHA {
    private import ScalarValues::*;
    private import SusanooLibrary::*;
    private import SusanooArchitecture::*;
    item def HealthExposure {
        attribute agent : HealthHazardAgent;
        attribute source : String;
        attribute exposedPopulation : String;
        attribute exposureLimitRef : String;
        attribute measured : Boolean;
    }
    enum def HealthHazardAgent {
        enum Acoustic;
        enum Vibration;
        enum Chemical;
        enum Thermal;
        enum Ergonomic;
        enum Biological;
        enum Radiation;
    }
}
