// Task202_PHA — generated by tools/gen_safety_docs.py from safety/mil-std-882e/catalog.yaml.
// Do not edit by hand: change the catalog and regenerate.
// Status: planning view only; not evidence of completed analysis or verification.

package Task202_PHA {
    private import ScalarValues::*;
    private import SusanooLibrary::*;
    private import SusanooArchitecture::*;
    item def PHARow {
        attribute hazardId : String;
        attribute scenario : String;
        attribute cause : String;
        attribute effect : String;
        attribute initialRisk : RiskAssessment;
        attribute candidateControl : String;
        ref item requirements : SafetyRequirement[0..*];
    }
}
