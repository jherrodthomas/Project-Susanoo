// Task210_EHA — generated by tools/gen_safety_docs.py from safety/mil-std-882e/catalog.yaml.
// Do not edit by hand: change the catalog and regenerate.
// Status: planning view only; not evidence of completed analysis or verification.

package Task210_EHA {
    private import ScalarValues::*;
    private import SusanooLibrary::*;
    private import SusanooArchitecture::*;
    item def EnvironmentalAspect {
        attribute aspect : String;
        attribute lifecyclePhase : LifecyclePhase;
        attribute receptor : String;
        attribute regulatoryRef : String;
    }
    enum def LifecyclePhase {
        enum Manufacture;
        enum Test;
        enum Operation;
        enum Maintenance;
        enum Transport;
        enum Disposal;
    }
}
