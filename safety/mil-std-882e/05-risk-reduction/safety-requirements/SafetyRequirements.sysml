// SafetyRequirements — generated by tools/gen_safety_docs.py from safety/mil-std-882e/catalog.yaml.
// Do not edit by hand: change the catalog and regenerate.
// Status: planning view only; not evidence of completed analysis or verification.

package SafetyRequirements {
    private import ScalarValues::*;
    private import SusanooLibrary::*;
    private import SusanooArchitecture::*;
    private import RequirementDerivation::*;
    private import SusanooRequirements::*;
    // Requirement records shown here are owned by models/sysml/model/Requirements.sysml (generated from requirements/); satisfy relations by Satisfaction.sysml.
    view requirementsInScope {
        expose SusanooRequirements::'SYS-002';
        expose SusanooRequirements::'SYS-010';
        expose SusanooRequirements::'SYS-011';
        expose SusanooRequirements::'SYS-003';
        expose SusanooRequirements::'SYS-012';
    }
    #derivation connection { end #original ::> SusanooRequirements::'SYS-002'; end #derive ::> SusanooRequirements::'SYS-010'; }
    #derivation connection { end #original ::> SusanooRequirements::'SYS-002'; end #derive ::> SusanooRequirements::'SYS-011'; }
    #derivation connection { end #original ::> SusanooRequirements::'SYS-003'; end #derive ::> SusanooRequirements::'SYS-012'; }
}
