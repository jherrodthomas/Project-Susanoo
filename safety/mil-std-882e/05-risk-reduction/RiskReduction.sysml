// RiskReduction — generated by tools/gen_safety_docs.py from safety/mil-std-882e/catalog.yaml.
// Do not edit by hand: change the catalog and regenerate.
// Status: planning view only; not evidence of completed analysis or verification.

package RiskReduction {
    private import ScalarValues::*;
    private import SusanooLibrary::*;
    private import SusanooArchitecture::*;
    item def MitigationImplementation {
        attribute mitigationId : String;
        attribute allocatedTo : String;
        attribute designRef : String;
        attribute status : String;
        ref item mitigation : Mitigation[1];
        ref item requirements : SafetyRequirement[1..*];
    }
}
