// MitigationIdentification — generated by tools/gen_safety_docs.py from safety/mil-std-882e/catalog.yaml.
// Do not edit by hand: change the catalog and regenerate.
// Status: planning view only; not evidence of completed analysis or verification.

package MitigationIdentification {
    private import ScalarValues::*;
    private import SusanooLibrary::*;
    private import SusanooArchitecture::*;
    action def DesignOrderOfPrecedence {
        action eliminate { doc /* Eliminate hazard through design selection */ }
        action reduceByDesign { doc /* Reduce risk through design alteration */ }
        action engineeredFeatures { doc /* Incorporate engineered safety features */ }
        action warningDevices { doc /* Incorporate detection and warning devices */ }
        action procedures { doc /* Signage, procedures, training and PPE */ }
        first start then eliminate;
        first eliminate then reduceByDesign;
        first reduceByDesign then engineeredFeatures;
        first engineeredFeatures then warningDevices;
        first warningDevices then procedures;
        first procedures then done;
        // iteration: procedures -> eliminate when residual risk too high (informal; merge node omitted)
    }
}
