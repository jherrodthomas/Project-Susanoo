// SafetyProgramFlow — generated by tools/gen_safety_docs.py from safety/mil-std-882e/catalog.yaml.
// Do not edit by hand: change the catalog and regenerate.
// Status: planning view only; not evidence of completed analysis or verification.

package SafetyProgramFlow {
    private import ScalarValues::*;
    private import SusanooLibrary::*;
    private import SusanooArchitecture::*;
    action def SystemSafetyProcess {
        doc /* Iterative MIL-STD-882E process applied to SUS-I1 configurations. */
        action documentApproach { doc /* 1 Document approach - SSPP, HMP */ }
        action identifyHazards { doc /* 2 Identify hazards - PHL, PHA, SSHA, SHA... */ }
        action assessRisk { doc /* 3 Assess risk - severity x probability */ }
        action identifyMitigations { doc /* 4 Identify mitigations - order of precedence */ }
        action reduceRisk { doc /* 5 Reduce risk - safety requirements in design */ }
        action verifyRiskReduction { doc /* 6 Verify risk reduction - Task 401 evidence */ }
        action acceptRisk { doc /* 7 Accept risk - authorized human decision */ }
        action manageLifecycleRisk { doc /* 8 Manage life-cycle risk - changes, mishaps */ }
        first start then documentApproach;
        first documentApproach then identifyHazards;
        first identifyHazards then assessRisk;
        first assessRisk then identifyMitigations;
        first identifyMitigations then reduceRisk;
        first reduceRisk then verifyRiskReduction;
        first verifyRiskReduction then acceptRisk;
        first acceptRisk then manageLifecycleRisk;
        first manageLifecycleRisk then done;
        // iteration: manageLifecycleRisk -> identifyHazards when change or new hazard (informal; merge node omitted)
        // iteration: verifyRiskReduction -> identifyMitigations when verification failed (informal; merge node omitted)
    }
}
