// Task107_ProgressReport — generated by tools/gen_safety_docs.py from safety/mil-std-882e/catalog.yaml.
// Do not edit by hand: change the catalog and regenerate.
// Status: planning view only; not evidence of completed analysis or verification.

package Task107_ProgressReport {
    private import ScalarValues::*;
    private import SusanooLibrary::*;
    private import SusanooArchitecture::*;
    item def ProgressReport {
        attribute period : String;
        attribute openCount : Integer;
        attribute closedCount : Integer;
        attribute highRiskOpen : Integer;
        attribute overdueActions : Integer;
    }
}
