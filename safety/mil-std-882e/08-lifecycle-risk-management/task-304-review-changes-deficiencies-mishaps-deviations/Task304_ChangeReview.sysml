// Task304_ChangeReview — generated by tools/gen_safety_docs.py from safety/mil-std-882e/catalog.yaml.
// Do not edit by hand: change the catalog and regenerate.
// Status: planning view only; not evidence of completed analysis or verification.

package Task304_ChangeReview {
    private import ScalarValues::*;
    private import SusanooLibrary::*;
    private import SusanooArchitecture::*;
    action def ChangeSafetyReview {
        action intake { doc /* Log change or event */ }
        action screen { doc /* Screen for safety impact */ }
        action analyse { doc /* Analyse affected hazards and controls */ }
        action recordDisposition { doc /* Record disposition and actions */ }
        first start then intake;
        first intake then screen;
        first screen then analyse;
        first analyse then recordDisposition;
        first recordDisposition then done;
        // iteration: recordDisposition -> screen when new information (informal; merge node omitted)
    }
}
