// LifecycleRisk — generated by tools/gen_safety_docs.py from safety/mil-std-882e/catalog.yaml.
// Do not edit by hand: change the catalog and regenerate.
// Status: planning view only; not evidence of completed analysis or verification.

package LifecycleRisk {
    private import ScalarValues::*;
    private import SusanooLibrary::*;
    private import SusanooArchitecture::*;
    action def ManageLifecycleRisk {
        action receive { doc /* Receive change, deficiency, mishap or deviation */ }
        action impact { doc /* Assess safety impact on hazards and controls */ }
        action reanalyse { doc /* Reopen affected analyses */ }
        action reverify { doc /* Re-verify affected controls */ }
        action redecide { doc /* Re-request acceptance if risk changed */ }
        first start then receive;
        first receive then impact;
        first impact then reanalyse;
        first reanalyse then reverify;
        first reverify then redecide;
        first redecide then done;
    }
}
