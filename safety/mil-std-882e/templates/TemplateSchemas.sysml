// TemplateSchemas — generated by tools/gen_safety_docs.py from safety/mil-std-882e/catalog.yaml.
// Do not edit by hand: change the catalog and regenerate.
// Status: planning view only; not evidence of completed analysis or verification.

package TemplateSchemas {
    private import ScalarValues::*;
    private import SusanooLibrary::*;
    private import SusanooArchitecture::*;
    item def TaskRecord {
        attribute taskId : Integer;
        attribute artifactId : String;
        attribute revision : String;
        attribute configurationId : String;
        attribute decision : String;
        ref item hazards : Hazard[0..*];
        ref item requirements : SafetyRequirement[0..*];
        ref item evidence : VerificationEvidence[0..*];
    }
}
