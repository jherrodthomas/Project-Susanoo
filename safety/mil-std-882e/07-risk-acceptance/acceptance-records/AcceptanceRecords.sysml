// AcceptanceRecords — generated by tools/gen_safety_docs.py from safety/mil-std-882e/catalog.yaml.
// Do not edit by hand: change the catalog and regenerate.
// Status: planning view only; not evidence of completed analysis or verification.

package AcceptanceRecords {
    private import ScalarValues::*;
    private import SusanooLibrary::*;
    private import SusanooArchitecture::*;
    item def AcceptanceRecord {
        attribute recordId : String;
        attribute hazardIds : String;
        attribute configurationId : String;
        attribute conditions : String;
        attribute expiresOnChange : Boolean;
        ref item decision : RiskAcceptanceDecision[1];
    }
}
