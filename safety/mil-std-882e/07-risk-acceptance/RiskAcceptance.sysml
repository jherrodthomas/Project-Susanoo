// RiskAcceptance — generated by tools/gen_safety_docs.py from safety/mil-std-882e/catalog.yaml.
// Do not edit by hand: change the catalog and regenerate.
// Status: planning view only; not evidence of completed analysis or verification.

package RiskAcceptance {
    private import ScalarValues::*;
    private import SusanooLibrary::*;
    private import SusanooArchitecture::*;
    attribute def AuthoritySigns;
    attribute def ConfigurationOrConopsChange;
    attribute def FurtherMitigationRequired;
    attribute def PackageComplete;
    attribute def Reassessed;
    state def RiskAcceptanceDecisionFlow {
        entry; then Requested;
        state Requested;
        state UnderReview;
        state Accepted { doc /* authority and record named */ }
        state Rejected;
        state Expired { doc /* configuration changed */ }
        transition t1 first Requested accept PackageComplete then UnderReview;
        transition t2 first UnderReview accept AuthoritySigns then Accepted;
        transition t3 first UnderReview accept FurtherMitigationRequired then Rejected;
        transition t4 first Accepted accept ConfigurationOrConopsChange then Expired;
        transition t5 first Expired accept Reassessed then Requested;
    }
}
