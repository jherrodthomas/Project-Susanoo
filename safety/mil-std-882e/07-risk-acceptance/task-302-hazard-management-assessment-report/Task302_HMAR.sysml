// Task302_HMAR — generated by tools/gen_safety_docs.py from safety/mil-std-882e/catalog.yaml.
// Do not edit by hand: change the catalog and regenerate.
// Status: planning view only; not evidence of completed analysis or verification.

package Task302_HMAR {
    private import ScalarValues::*;
    private import SusanooLibrary::*;
    private import SusanooArchitecture::*;
    item def HazardManagementAssessmentReport {
        attribute milestone : String;
        attribute configurationId : String;
        attribute openHigh : Integer;
        attribute openSerious : Integer;
        ref item hazards : Hazard[0..*];
    }
}
