// Task301_SAR — generated by tools/gen_safety_docs.py from safety/mil-std-882e/catalog.yaml.
// Do not edit by hand: change the catalog and regenerate.
// Status: planning view only; not evidence of completed analysis or verification.

package Task301_SAR {
    private import ScalarValues::*;
    private import SusanooLibrary::*;
    private import SusanooArchitecture::*;
    item def SafetyAssessmentReport {
        attribute configurationId : String;
        attribute revision : String;
        ref item hazards : Hazard[0..*];
        ref item evidence : VerificationEvidence[0..*];
        ref item limitations : OperatingLimitation[0..*];
    }
    item def OperatingLimitation {
        attribute text : String;
        attribute hazardId : String;
    }
}
