// SoftwareSafety — generated by tools/gen_safety_docs.py from safety/mil-std-882e/catalog.yaml.
// Do not edit by hand: change the catalog and regenerate.
// Status: planning view only; not evidence of completed analysis or verification.

package SoftwareSafety {
    private import ScalarValues::*;
    private import SusanooLibrary::*;
    private import SusanooArchitecture::*;
    item def SoftwareFunctionAssessment {
        attribute functionId : String;
        attribute controlCategory : SoftwareControlCategory;
        attribute severity : SeverityCategory;
        attribute levelOfRigor : String;
        attribute independentMitigation : Boolean;
    }
}
