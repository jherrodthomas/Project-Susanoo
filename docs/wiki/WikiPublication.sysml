// WikiPublication — generated by tools/figures/wiki_readme.py from .github/workflows/publish-wiki.yml.
// Do not edit by hand: change the workflow or the generator and regenerate.
// Status: documentation publishing; publishing a page reviews or accepts nothing.

package WikiPublication {
    doc /* How the wiki source in docs/wiki is published (docs/wiki/README.md). */
    action def PublishWiki {
        doc /* The steps of .github/workflows/publish-wiki.yml, read from the workflow. */
        action checkOutTheHandbookSource { doc /* Check out the handbook source */ }
        action checkTheWikiDeployCredential { doc /* Check the wiki deploy credential */ }
        action cloneTheWikiRepository { doc /* Clone the wiki repository */ }
        action commitIfAnythingChanged { doc /* Commit, if anything changed */ }
        action pushToTheWikiRepository { doc /* Push to the wiki repository */ }
        first start then checkOutTheHandbookSource;
        first checkOutTheHandbookSource then checkTheWikiDeployCredential;
        first checkTheWikiDeployCredential then cloneTheWikiRepository;
        first cloneTheWikiRepository then commitIfAnythingChanged;
        first commitIfAnythingChanged then pushToTheWikiRepository;
        first pushToTheWikiRepository then done;
    }
}
