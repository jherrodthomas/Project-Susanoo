// WikiImages — generated by tools/figures/wikiimages_readme.py from docs/wiki/images.
// Do not edit by hand: regenerate the images or change the generator and regenerate.
// Status: documentation figures; nothing in them is reviewed or accepted.

package WikiImages {
    private import ScalarValues::*;
    doc /* The figures the wiki shows directly (docs/wiki/images/README.md). */
    part def WikiImage {
        doc /* A figure the wiki shows directly from images/. */
        attribute file : String;
        attribute kilobytes : Integer;
        attribute shownOn : Integer;
    }
    part def GeneratedFigure :> WikiImage {
        doc /* Written from the records by a generator; CI fails when it is stale. */
        attribute generator : String;
    }
    part def RenderedStill :> WikiImage {
        doc /* Rendered from an interactive page in headless Chromium by a CI check. */
        attribute page : String;
    }
    part def HandExport :> WikiImage {
        doc /* Exported by hand from its draw.io source; nothing checks it is current. */
        attribute source : String;
    }
    part img3DS301Dusk : RenderedStill {
        attribute :>> file = "3d-s3-01-dusk.png";
        attribute :>> kilobytes = 111;
        attribute :>> shownOn = 5;
        attribute :>> page = "sim/scenes3d/render.mjs";
    }
    part img3DS301 : RenderedStill {
        attribute :>> file = "3d-s3-01.png";
        attribute :>> kilobytes = 123;
        attribute :>> shownOn = 3;
        attribute :>> page = "sim/scenes3d/render.mjs";
    }
    part img3DS302 : RenderedStill {
        attribute :>> file = "3d-s3-02.png";
        attribute :>> kilobytes = 83;
        attribute :>> shownOn = 3;
        attribute :>> page = "sim/scenes3d/render.mjs";
    }
    part img3DS303 : RenderedStill {
        attribute :>> file = "3d-s3-03.png";
        attribute :>> kilobytes = 77;
        attribute :>> shownOn = 3;
        attribute :>> page = "sim/scenes3d/render.mjs";
    }
    part img3DS304 : RenderedStill {
        attribute :>> file = "3d-s3-04.png";
        attribute :>> kilobytes = 102;
        attribute :>> shownOn = 3;
        attribute :>> page = "sim/scenes3d/render.mjs";
    }
    part img3DS305Fog : RenderedStill {
        attribute :>> file = "3d-s3-05-fog.png";
        attribute :>> kilobytes = 57;
        attribute :>> shownOn = 3;
        attribute :>> page = "sim/scenes3d/render.mjs";
    }
    part img3DS305 : RenderedStill {
        attribute :>> file = "3d-s3-05.png";
        attribute :>> kilobytes = 61;
        attribute :>> shownOn = 3;
        attribute :>> page = "sim/scenes3d/render.mjs";
    }
    part img3DS306 : RenderedStill {
        attribute :>> file = "3d-s3-06.png";
        attribute :>> kilobytes = 70;
        attribute :>> shownOn = 3;
        attribute :>> page = "sim/scenes3d/render.mjs";
    }
    part img3DSusA1Air : RenderedStill {
        attribute :>> file = "3d-sus-a1-air.png";
        attribute :>> kilobytes = 291;
        attribute :>> shownOn = 5;
        attribute :>> page = "sim/scenes3d/sheet_check.mjs";
    }
    part img3DSusA1Lr : RenderedStill {
        attribute :>> file = "3d-sus-a1-lr.png";
        attribute :>> kilobytes = 335;
        attribute :>> shownOn = 5;
        attribute :>> page = "sim/scenes3d/sheet_check.mjs";
    }
    part img3DSusA1 : RenderedStill {
        attribute :>> file = "3d-sus-a1.png";
        attribute :>> kilobytes = 468;
        attribute :>> shownOn = 5;
        attribute :>> page = "sim/scenes3d/sheet_check.mjs";
    }
    part img3DSusM1TerrainLoaded : RenderedStill {
        attribute :>> file = "3d-sus-m1-terrain-loaded.png";
        attribute :>> kilobytes = 310;
        attribute :>> shownOn = 5;
        attribute :>> page = "sim/scenes3d/sheet_check.mjs";
    }
    part img3DSusM1Terrain : RenderedStill {
        attribute :>> file = "3d-sus-m1-terrain.png";
        attribute :>> kilobytes = 312;
        attribute :>> shownOn = 5;
        attribute :>> page = "sim/scenes3d/sheet_check.mjs";
    }
    part img3DSusM1 : RenderedStill {
        attribute :>> file = "3d-sus-m1.png";
        attribute :>> kilobytes = 388;
        attribute :>> shownOn = 5;
        attribute :>> page = "sim/scenes3d/sheet_check.mjs";
    }
    part imgAnalysisDependencies : HandExport {
        attribute :>> file = "analysis-dependencies.svg";
        attribute :>> kilobytes = 6;
        attribute :>> shownOn = 8;
        attribute :>> source = "docs/diagrams/mil-std-882e/analysis-dependencies.drawio";
    }
    part imgHazardManagement : HandExport {
        attribute :>> file = "hazard-management.svg";
        attribute :>> kilobytes = 5;
        attribute :>> shownOn = 8;
        attribute :>> source = "docs/diagrams/mil-std-882e/hazard-management.drawio";
    }
    part imgRecAcceptance : GeneratedFigure {
        attribute :>> file = "rec-acceptance.svg";
        attribute :>> kilobytes = 18;
        attribute :>> shownOn = 1;
        attribute :>> generator = "tools/previews/record_figures.py";
    }
    part imgRecDecisionBoard : GeneratedFigure {
        attribute :>> file = "rec-decision-board.svg";
        attribute :>> kilobytes = 36;
        attribute :>> shownOn = 0;
        attribute :>> generator = "tools/previews/record_figures.py";
    }
    part imgRecEventRisk : GeneratedFigure {
        attribute :>> file = "rec-event-risk.svg";
        attribute :>> kilobytes = 19;
        attribute :>> shownOn = 1;
        attribute :>> generator = "tools/previews/record_figures.py";
    }
    part imgRecL1L2 : GeneratedFigure {
        attribute :>> file = "rec-l1-l2.svg";
        attribute :>> kilobytes = 32;
        attribute :>> shownOn = 0;
        attribute :>> generator = "tools/previews/record_figures.py";
    }
    part imgRecMitigations : GeneratedFigure {
        attribute :>> file = "rec-mitigations.svg";
        attribute :>> kilobytes = 42;
        attribute :>> shownOn = 1;
        attribute :>> generator = "tools/previews/record_figures.py";
    }
    part imgRecRecordModel : GeneratedFigure {
        attribute :>> file = "rec-record-model.svg";
        attribute :>> kilobytes = 24;
        attribute :>> shownOn = 2;
        attribute :>> generator = "tools/previews/record_figures.py";
    }
    part imgRecSsf : GeneratedFigure {
        attribute :>> file = "rec-ssf.svg";
        attribute :>> kilobytes = 28;
        attribute :>> shownOn = 1;
        attribute :>> generator = "tools/previews/record_figures.py";
    }
    part imgRecTaskTailoring : GeneratedFigure {
        attribute :>> file = "rec-task-tailoring.svg";
        attribute :>> kilobytes = 25;
        attribute :>> shownOn = 1;
        attribute :>> generator = "tools/previews/record_figures.py";
    }
    part imgRecTraceability : GeneratedFigure {
        attribute :>> file = "rec-traceability.svg";
        attribute :>> kilobytes = 76;
        attribute :>> shownOn = 0;
        attribute :>> generator = "tools/previews/record_figures.py";
    }
    part imgRelBands : GeneratedFigure {
        attribute :>> file = "rel-bands.svg";
        attribute :>> kilobytes = 10;
        attribute :>> shownOn = 2;
        attribute :>> generator = "tools/reliability/build.py";
    }
    part imgRelFt001 : GeneratedFigure {
        attribute :>> file = "rel-ft-001.svg";
        attribute :>> kilobytes = 6;
        attribute :>> shownOn = 2;
        attribute :>> generator = "tools/reliability/build.py";
    }
    part imgRelFt002 : GeneratedFigure {
        attribute :>> file = "rel-ft-002.svg";
        attribute :>> kilobytes = 9;
        attribute :>> shownOn = 2;
        attribute :>> generator = "tools/reliability/build.py";
    }
    part imgRelFt003 : GeneratedFigure {
        attribute :>> file = "rel-ft-003.svg";
        attribute :>> kilobytes = 9;
        attribute :>> shownOn = 2;
        attribute :>> generator = "tools/reliability/build.py";
    }
    part imgRelFt004 : GeneratedFigure {
        attribute :>> file = "rel-ft-004.svg";
        attribute :>> kilobytes = 6;
        attribute :>> shownOn = 1;
        attribute :>> generator = "tools/reliability/build.py";
    }
    part imgRelFt005 : GeneratedFigure {
        attribute :>> file = "rel-ft-005.svg";
        attribute :>> kilobytes = 8;
        attribute :>> shownOn = 1;
        attribute :>> generator = "tools/reliability/build.py";
    }
    part imgRelFt006 : GeneratedFigure {
        attribute :>> file = "rel-ft-006.svg";
        attribute :>> kilobytes = 7;
        attribute :>> shownOn = 1;
        attribute :>> generator = "tools/reliability/build.py";
    }
    part imgRelFt007 : GeneratedFigure {
        attribute :>> file = "rel-ft-007.svg";
        attribute :>> kilobytes = 7;
        attribute :>> shownOn = 1;
        attribute :>> generator = "tools/reliability/build.py";
    }
    part imgRelFt008 : GeneratedFigure {
        attribute :>> file = "rel-ft-008.svg";
        attribute :>> kilobytes = 4;
        attribute :>> shownOn = 1;
        attribute :>> generator = "tools/reliability/build.py";
    }
    part imgRelFt009 : GeneratedFigure {
        attribute :>> file = "rel-ft-009.svg";
        attribute :>> kilobytes = 10;
        attribute :>> shownOn = 2;
        attribute :>> generator = "tools/reliability/build.py";
    }
    part imgRelFt010 : GeneratedFigure {
        attribute :>> file = "rel-ft-010.svg";
        attribute :>> kilobytes = 6;
        attribute :>> shownOn = 1;
        attribute :>> generator = "tools/reliability/build.py";
    }
    part imgRelFt011 : GeneratedFigure {
        attribute :>> file = "rel-ft-011.svg";
        attribute :>> kilobytes = 5;
        attribute :>> shownOn = 1;
        attribute :>> generator = "tools/reliability/build.py";
    }
    part imgRelFt012 : GeneratedFigure {
        attribute :>> file = "rel-ft-012.svg";
        attribute :>> kilobytes = 5;
        attribute :>> shownOn = 1;
        attribute :>> generator = "tools/reliability/build.py";
    }
    part imgRelFt013 : GeneratedFigure {
        attribute :>> file = "rel-ft-013.svg";
        attribute :>> kilobytes = 8;
        attribute :>> shownOn = 1;
        attribute :>> generator = "tools/reliability/build.py";
    }
    part imgRelFt014 : GeneratedFigure {
        attribute :>> file = "rel-ft-014.svg";
        attribute :>> kilobytes = 5;
        attribute :>> shownOn = 1;
        attribute :>> generator = "tools/reliability/build.py";
    }
    part imgRelFt015 : GeneratedFigure {
        attribute :>> file = "rel-ft-015.svg";
        attribute :>> kilobytes = 5;
        attribute :>> shownOn = 1;
        attribute :>> generator = "tools/reliability/build.py";
    }
    part imgRelFt016 : GeneratedFigure {
        attribute :>> file = "rel-ft-016.svg";
        attribute :>> kilobytes = 4;
        attribute :>> shownOn = 1;
        attribute :>> generator = "tools/reliability/build.py";
    }
    part imgRelFt017 : GeneratedFigure {
        attribute :>> file = "rel-ft-017.svg";
        attribute :>> kilobytes = 5;
        attribute :>> shownOn = 1;
        attribute :>> generator = "tools/reliability/build.py";
    }
    part imgRelFt018 : GeneratedFigure {
        attribute :>> file = "rel-ft-018.svg";
        attribute :>> kilobytes = 5;
        attribute :>> shownOn = 1;
        attribute :>> generator = "tools/reliability/build.py";
    }
    part imgRelFt019 : GeneratedFigure {
        attribute :>> file = "rel-ft-019.svg";
        attribute :>> kilobytes = 6;
        attribute :>> shownOn = 1;
        attribute :>> generator = "tools/reliability/build.py";
    }
    part imgRelFt020 : GeneratedFigure {
        attribute :>> file = "rel-ft-020.svg";
        attribute :>> kilobytes = 5;
        attribute :>> shownOn = 1;
        attribute :>> generator = "tools/reliability/build.py";
    }
    part imgRelFt021 : GeneratedFigure {
        attribute :>> file = "rel-ft-021.svg";
        attribute :>> kilobytes = 8;
        attribute :>> shownOn = 2;
        attribute :>> generator = "tools/reliability/build.py";
    }
    part imgRelFt022 : GeneratedFigure {
        attribute :>> file = "rel-ft-022.svg";
        attribute :>> kilobytes = 6;
        attribute :>> shownOn = 1;
        attribute :>> generator = "tools/reliability/build.py";
    }
    part imgRelFt023 : GeneratedFigure {
        attribute :>> file = "rel-ft-023.svg";
        attribute :>> kilobytes = 6;
        attribute :>> shownOn = 1;
        attribute :>> generator = "tools/reliability/build.py";
    }
    part imgRelFt024 : GeneratedFigure {
        attribute :>> file = "rel-ft-024.svg";
        attribute :>> kilobytes = 7;
        attribute :>> shownOn = 1;
        attribute :>> generator = "tools/reliability/build.py";
    }
    part imgResponsibilitySwimlanes : HandExport {
        attribute :>> file = "responsibility-swimlanes.svg";
        attribute :>> kilobytes = 5;
        attribute :>> shownOn = 8;
        attribute :>> source = "docs/diagrams/mil-std-882e/responsibility-swimlanes.drawio";
    }
    part imgSafetyLifecycle : HandExport {
        attribute :>> file = "safety-lifecycle.svg";
        attribute :>> kilobytes = 7;
        attribute :>> shownOn = 8;
        attribute :>> source = "docs/diagrams/mil-std-882e/safety-lifecycle.drawio";
    }
    part imgSimSc01 : GeneratedFigure {
        attribute :>> file = "sim-sc-01.svg";
        attribute :>> kilobytes = 19;
        attribute :>> shownOn = 5;
        attribute :>> generator = "sim/figures/scenes.py";
    }
    part imgSimSc02 : GeneratedFigure {
        attribute :>> file = "sim-sc-02.svg";
        attribute :>> kilobytes = 18;
        attribute :>> shownOn = 3;
        attribute :>> generator = "sim/figures/scenes.py";
    }
    part imgSimSc03 : GeneratedFigure {
        attribute :>> file = "sim-sc-03.svg";
        attribute :>> kilobytes = 18;
        attribute :>> shownOn = 3;
        attribute :>> generator = "sim/figures/scenes.py";
    }
    part imgSimSc04 : GeneratedFigure {
        attribute :>> file = "sim-sc-04.svg";
        attribute :>> kilobytes = 18;
        attribute :>> shownOn = 3;
        attribute :>> generator = "sim/figures/scenes.py";
    }
    part imgSimSu01 : GeneratedFigure {
        attribute :>> file = "sim-su-01.svg";
        attribute :>> kilobytes = 9;
        attribute :>> shownOn = 3;
        attribute :>> generator = "sim/figures/uav_scenes.py";
    }
    part imgSimSu02 : GeneratedFigure {
        attribute :>> file = "sim-su-02.svg";
        attribute :>> kilobytes = 9;
        attribute :>> shownOn = 3;
        attribute :>> generator = "sim/figures/uav_scenes.py";
    }
    part imgSimSu03 : GeneratedFigure {
        attribute :>> file = "sim-su-03.svg";
        attribute :>> kilobytes = 7;
        attribute :>> shownOn = 3;
        attribute :>> generator = "sim/figures/uav_scenes.py";
    }
    part imgSimSu04 : GeneratedFigure {
        attribute :>> file = "sim-su-04.svg";
        attribute :>> kilobytes = 7;
        attribute :>> shownOn = 3;
        attribute :>> generator = "sim/figures/uav_scenes.py";
    }
    part imgSimSu05 : GeneratedFigure {
        attribute :>> file = "sim-su-05.svg";
        attribute :>> kilobytes = 12;
        attribute :>> shownOn = 3;
        attribute :>> generator = "sim/figures/uav_scenes.py";
    }
    part imgSimSu06 : GeneratedFigure {
        attribute :>> file = "sim-su-06.svg";
        attribute :>> kilobytes = 8;
        attribute :>> shownOn = 3;
        attribute :>> generator = "sim/figures/uav_scenes.py";
    }
    part imgSoftwareSafety : HandExport {
        attribute :>> file = "software-safety.svg";
        attribute :>> kilobytes = 6;
        attribute :>> shownOn = 8;
        attribute :>> source = "docs/diagrams/mil-std-882e/software-safety.drawio";
    }
    part imgSusI1Boundary : GeneratedFigure {
        attribute :>> file = "sus-i1-boundary.svg";
        attribute :>> kilobytes = 28;
        attribute :>> shownOn = 4;
        attribute :>> generator = "tools/figures/fig_item.py";
    }
    part imgSusI1Context : GeneratedFigure {
        attribute :>> file = "sus-i1-context.svg";
        attribute :>> kilobytes = 17;
        attribute :>> shownOn = 7;
        attribute :>> generator = "tools/figures/fig_item.py";
    }
    part imgSysmlV02Hierarchy : GeneratedFigure {
        attribute :>> file = "sysml-v02-hierarchy.svg";
        attribute :>> kilobytes = 19;
        attribute :>> shownOn = 5;
        attribute :>> generator = "tools/sysml/views.py";
    }
    part imgSysmlV07Satisfy : GeneratedFigure {
        attribute :>> file = "sysml-v07-satisfy.svg";
        attribute :>> kilobytes = 16;
        attribute :>> shownOn = 5;
        attribute :>> generator = "tools/sysml/views.py";
    }
    part imgSysmlV08N2 : GeneratedFigure {
        attribute :>> file = "sysml-v08-n2.svg";
        attribute :>> kilobytes = 93;
        attribute :>> shownOn = 7;
        attribute :>> generator = "tools/sysml/views.py";
    }
    part imgVcycleSystem : GeneratedFigure {
        attribute :>> file = "vcycle-system.svg";
        attribute :>> kilobytes = 9;
        attribute :>> shownOn = 4;
        attribute :>> generator = "tools/vcycle/build_vcycle.py";
    }
    part imgVerificationChange : HandExport {
        attribute :>> file = "verification-change.svg";
        attribute :>> kilobytes = 5;
        attribute :>> shownOn = 7;
        attribute :>> source = "docs/diagrams/mil-std-882e/verification-change.drawio";
    }
    part imgWikiFig1Pages : GeneratedFigure {
        attribute :>> file = "wiki-fig-1-pages.svg";
        attribute :>> kilobytes = 58;
        attribute :>> shownOn = 1;
        attribute :>> generator = "tools/figures/wiki_readme.py";
    }
    part imgWikiFig2Links : GeneratedFigure {
        attribute :>> file = "wiki-fig-2-links.svg";
        attribute :>> kilobytes = 13;
        attribute :>> shownOn = 1;
        attribute :>> generator = "tools/figures/wiki_readme.py";
    }
    part imgWikiFig3BlockDiagram : GeneratedFigure {
        attribute :>> file = "wiki-fig-3-block-diagram.svg";
        attribute :>> kilobytes = 27;
        attribute :>> shownOn = 1;
        attribute :>> generator = "tools/figures/wiki_readme.py";
    }
    part imgWikiFig4BoundaryDiagram : GeneratedFigure {
        attribute :>> file = "wiki-fig-4-boundary-diagram.svg";
        attribute :>> kilobytes = 17;
        attribute :>> shownOn = 1;
        attribute :>> generator = "tools/figures/wiki_readme.py";
    }
    part imgWikiFig5SysmlActivity : GeneratedFigure {
        attribute :>> file = "wiki-fig-5-sysml-activity.svg";
        attribute :>> kilobytes = 12;
        attribute :>> shownOn = 1;
        attribute :>> generator = "tools/figures/wiki_readme.py";
    }
    part imgWikiFig6InputsAndOutputs : GeneratedFigure {
        attribute :>> file = "wiki-fig-6-inputs-and-outputs.svg";
        attribute :>> kilobytes = 14;
        attribute :>> shownOn = 1;
        attribute :>> generator = "tools/figures/wiki_readme.py";
    }
}
