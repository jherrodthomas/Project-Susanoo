// MapActivities — generated by tools/figures/maps882e_readme.py from the draw.io sources in docs/diagrams/mil-std-882e.
// Do not edit by hand: change a source or the generator and regenerate.
// Status: illustrative draft workflows; not normative flowcharts or evidence of completed tasks.

package MapActivities {
    doc /* The six MIL-STD-882E process maps as activities (docs/diagrams/mil-std-882e/README.md). */
    action def AnalysisDependencies {
        doc /* Hazard analysis relationships (analysis-dependencies.drawio): Analyses inform each other; the arrows are information flow, not mandatory sequencing. */
        action conceptConopsPhl { doc /* Concept: CONOPS / PHL */ }
        action conceptPha { doc /* Concept: PHA */ }
        action requirementsSrha { doc /* Requirements: SRHA */ }
        action requirementsFha { doc /* Requirements: FHA */ }
        action subsystemsSsha { doc /* Subsystems: SSHA */ }
        action subsystemsInterfaceHazards { doc /* Subsystems: Interface hazards */ }
        action integrationSha { doc /* Integration: SHA */ }
        action integrationOShaHhaEha { doc /* Integration: O&SHA / HHA / EHA */ }
        first start then conceptConopsPhl;
        first conceptConopsPhl then conceptPha;
        first conceptPha then requirementsSrha;
        first requirementsSrha then requirementsFha;
        first requirementsFha then subsystemsSsha;
        first subsystemsSsha then subsystemsInterfaceHazards;
        first subsystemsInterfaceHazards then integrationSha;
        first integrationSha then integrationOShaHhaEha;
        first integrationOShaHhaEha then done;
    }
    action def HazardManagement {
        doc /* Hazard management and risk acceptance (hazard-management.drawio): Residual risk acceptance is a separate authorized decision, never automatic closure. */
        action safetyAnalystIdentifyHazard { doc /* Safety analyst: Identify hazard */ }
        action safetyAnalystAssessInitialRisk { doc /* Safety analyst: Assess initial risk */ }
        action systemsDesignSelectDesignMitigation { doc /* Systems & design: Select design mitigation */ }
        action systemsDesignImplementControl { doc /* Systems & design: Implement control */ }
        action verificationVerifyImplementation { doc /* Verification: Verify implementation */ }
        action verificationValidateRiskReduction { doc /* Verification: Validate risk reduction */ }
        action riskAuthorityReviewResidualRisk { doc /* Risk authority: Review residual risk */ }
        action riskAuthorityAcceptRejectReturn { doc /* Risk authority: Accept / reject / return */ }
        first start then safetyAnalystIdentifyHazard;
        first safetyAnalystIdentifyHazard then safetyAnalystAssessInitialRisk;
        first safetyAnalystAssessInitialRisk then systemsDesignSelectDesignMitigation;
        first systemsDesignSelectDesignMitigation then systemsDesignImplementControl;
        first systemsDesignImplementControl then verificationVerifyImplementation;
        first verificationVerifyImplementation then verificationValidateRiskReduction;
        first verificationValidateRiskReduction then riskAuthorityReviewResidualRisk;
        first riskAuthorityReviewResidualRisk then riskAuthorityAcceptRejectReturn;
        first riskAuthorityAcceptRejectReturn then done;
    }
    action def ResponsibilitySwimlanes {
        doc /* Safety responsibility swimlanes (responsibility-swimlanes.drawio): Every handoff requires an owner, configuration ID and evidence links. */
        action safetyLeadRegisterHazard { doc /* Safety lead: Register hazard */ }
        action safetyLeadProposeRiskRating { doc /* Safety lead: Propose risk rating */ }
        action systemsDesignAllocateSafetyRequirement { doc /* Systems / design: Allocate safety requirement */ }
        action systemsDesignImplementMitigation { doc /* Systems / design: Implement mitigation */ }
        action testLeadPlanVerification { doc /* Test lead: Plan verification */ }
        action testLeadCaptureObjectiveEvidence { doc /* Test lead: Capture objective evidence */ }
        action riskAuthorityReviewResidualRisk { doc /* Risk authority: Review residual risk */ }
        action riskAuthorityRecordAcceptanceDecision { doc /* Risk authority: Record acceptance decision */ }
        first start then safetyLeadRegisterHazard;
        first safetyLeadRegisterHazard then safetyLeadProposeRiskRating;
        first safetyLeadProposeRiskRating then systemsDesignAllocateSafetyRequirement;
        first systemsDesignAllocateSafetyRequirement then systemsDesignImplementMitigation;
        first systemsDesignImplementMitigation then testLeadPlanVerification;
        first testLeadPlanVerification then testLeadCaptureObjectiveEvidence;
        first testLeadCaptureObjectiveEvidence then riskAuthorityReviewResidualRisk;
        first riskAuthorityReviewResidualRisk then riskAuthorityRecordAcceptanceDecision;
        first riskAuthorityRecordAcceptanceDecision then done;
    }
    action def SafetyLifecycle {
        doc /* System safety lifecycle (safety-lifecycle.drawio): Iterative lifecycle: every configuration change can reopen hazard analysis. */
        action conceptScopeConopsBoundaries { doc /* Concept & scope: CONOPS + boundaries */ }
        action conceptScopeTailorTasksSspp { doc /* Concept & scope: Tailor tasks / SSPP */ }
        action analysisPhlPha { doc /* Analysis: PHL / PHA */ }
        action analysisSrhaFha { doc /* Analysis: SRHA / FHA */ }
        action designControlsSshaShaOSha { doc /* Design & controls: SSHA / SHA / O&SHA */ }
        action designControlsMitigationAllocation { doc /* Design & controls: Mitigation allocation */ }
        action evidenceReleaseVerifyControls { doc /* Evidence & release: Verify controls */ }
        action evidenceReleaseRiskDisposition { doc /* Evidence & release: Risk disposition */ }
        action sustainmentMonitorIncidents { doc /* Sustainment: Monitor incidents */ }
        action sustainmentReassessChanges { doc /* Sustainment: Reassess changes */ }
        first start then conceptScopeConopsBoundaries;
        first conceptScopeConopsBoundaries then conceptScopeTailorTasksSspp;
        first conceptScopeTailorTasksSspp then analysisPhlPha;
        first analysisPhlPha then analysisSrhaFha;
        first analysisSrhaFha then designControlsSshaShaOSha;
        first designControlsSshaShaOSha then designControlsMitigationAllocation;
        first designControlsMitigationAllocation then evidenceReleaseVerifyControls;
        first evidenceReleaseVerifyControls then evidenceReleaseRiskDisposition;
        first evidenceReleaseRiskDisposition then sustainmentMonitorIncidents;
        first sustainmentMonitorIncidents then sustainmentReassessChanges;
        first sustainmentReassessChanges then done;
    }
    action def SoftwareSafety {
        doc /* Software contribution to system risk (software-safety.drawio): PX4 flight-control software and walker control software remain distinct assurance boundaries. */
        action systemSafetyIdentifySoftwareHazardContribution { doc /* System safety: Identify software hazard contribution */ }
        action systemSafetyAssessCriticality { doc /* System safety: Assess criticality */ }
        action softwareEngineeringAllocateSoftwareSafetyRequirements { doc /* Software engineering: Allocate software safety requirements */ }
        action softwareEngineeringAnalyzeControlAuthority { doc /* Software engineering: Analyze control authority */ }
        action integrationTestTestFailureResponses { doc /* Integration & test: Test failure responses */ }
        action integrationTestFaultInjectionEvidence { doc /* Integration & test: Fault injection / evidence */ }
        action configurationPinVersionsParameters { doc /* Configuration: Pin versions + parameters */ }
        action configurationReassessAfterChange { doc /* Configuration: Reassess after change */ }
        first start then systemSafetyIdentifySoftwareHazardContribution;
        first systemSafetyIdentifySoftwareHazardContribution then systemSafetyAssessCriticality;
        first systemSafetyAssessCriticality then softwareEngineeringAllocateSoftwareSafetyRequirements;
        first softwareEngineeringAllocateSoftwareSafetyRequirements then softwareEngineeringAnalyzeControlAuthority;
        first softwareEngineeringAnalyzeControlAuthority then integrationTestTestFailureResponses;
        first integrationTestTestFailureResponses then integrationTestFaultInjectionEvidence;
        first integrationTestFaultInjectionEvidence then configurationPinVersionsParameters;
        first configurationPinVersionsParameters then configurationReassessAfterChange;
        first configurationReassessAfterChange then done;
    }
    action def VerificationChange {
        doc /* Safety verification and change control (verification-change.drawio): Failed tests or changed configurations trigger reanalysis and re-verification. */
        action requirementHazardMitigationTestCriteria { doc /* Requirement & hazard: Mitigation + test criteria */ }
        action requirementHazardTraceToHazard { doc /* Requirement & hazard: Trace to hazard */ }
        action verificationExecuteRecordTest { doc /* Verification: Execute / record test */ }
        action verificationInvestigateAnomalies { doc /* Verification: Investigate anomalies */ }
        action reviewReviewEffectiveness { doc /* Review: Review effectiveness */ }
        action reviewUpdateResidualRisk { doc /* Review: Update residual risk */ }
        action changeControlApproveDisposition { doc /* Change control: Approve disposition */ }
        action changeControlReopenOnChanges { doc /* Change control: Reopen on changes */ }
        first start then requirementHazardMitigationTestCriteria;
        first requirementHazardMitigationTestCriteria then requirementHazardTraceToHazard;
        first requirementHazardTraceToHazard then verificationExecuteRecordTest;
        first verificationExecuteRecordTest then verificationInvestigateAnomalies;
        first verificationInvestigateAnomalies then reviewReviewEffectiveness;
        first reviewReviewEffectiveness then reviewUpdateResidualRisk;
        first reviewUpdateResidualRisk then changeControlApproveDisposition;
        first changeControlApproveDisposition then changeControlReopenOnChanges;
        first changeControlReopenOnChanges then done;
    }
}
