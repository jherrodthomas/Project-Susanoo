// ProcessMaps — generated by tools/figures/diagrams_readme.py from docs/diagrams/mil-std-882e/safety-lifecycle.drawio.
// Do not edit by hand: change the draw.io source or the generator and regenerate.
// Status: illustrative draft workflow; not a normative flowchart or evidence of completed tasks.

package ProcessMaps {
    doc /* The MIL-STD-882E process maps (docs/diagrams/README.md). */
    action def SafetyLifecycle {
        doc /* System safety lifecycle, from docs/diagrams/mil-std-882e/safety-lifecycle.drawio: Iterative lifecycle: every configuration change can reopen hazard analysis. */
        action conopsBoundaries { doc /* Concept & scope: CONOPS + boundaries */ }
        action tailorTasksSspp { doc /* Concept & scope: Tailor tasks / SSPP */ }
        action phlPha { doc /* Analysis: PHL / PHA */ }
        action srhaFha { doc /* Analysis: SRHA / FHA */ }
        action sshaShaOSha { doc /* Design & controls: SSHA / SHA / O&SHA */ }
        action mitigationAllocation { doc /* Design & controls: Mitigation allocation */ }
        action verifyControls { doc /* Evidence & release: Verify controls */ }
        action riskDisposition { doc /* Evidence & release: Risk disposition */ }
        action monitorIncidents { doc /* Sustainment: Monitor incidents */ }
        action reassessChanges { doc /* Sustainment: Reassess changes */ }
        first start then conopsBoundaries;
        first conopsBoundaries then tailorTasksSspp;
        first tailorTasksSspp then phlPha;
        first phlPha then srhaFha;
        first srhaFha then sshaShaOSha;
        first sshaShaOSha then mitigationAllocation;
        first mitigationAllocation then verifyControls;
        first verifyControls then riskDisposition;
        first riskDisposition then monitorIncidents;
        first monitorIncidents then reassessChanges;
        first reassessChanges then done;
        // iteration: reassessChanges -> phlPha when configuration change (informal; merge node omitted)
    }
}
