// DocumentationState — generated by tools/figures/docs_readme.py.
// Do not edit by hand: change the generator and regenerate.
// Status: how a generated documentation file stays current; not a review.

package DocumentationState {
    doc /* Generated documentation files (docs/README.md; CLAUDE.md: never edit a generated file). */
    attribute def GeneratorReRunAndCommitted;
    attribute def MergedToMain;
    attribute def RecordOrGeneratorChanged;
    state def GeneratedFile {
        doc /* A generated documentation file: rebuilt from the records, never edited by hand, checked in CI. */
        entry; then Current;
        state Current { doc /* matches what its generator writes from the records */ }
        state Stale { doc /* a record or the generator changed; CI fails with --check */ }
        state Published { doc /* on main; wiki pages copied to the GitHub Wiki */ }
        transition t1 first Current accept RecordOrGeneratorChanged then Stale;
        transition t2 first Stale accept GeneratorReRunAndCommitted then Current;
        transition t3 first Current accept MergedToMain then Published;
        transition t4 first Published accept RecordOrGeneratorChanged then Stale;
    }
}
