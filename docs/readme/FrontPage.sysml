// FrontPage — generated by tools/figures/frontpage_readme.py from tools/readme/build_readme.py main().
// Do not edit by hand: change the builder or the generator and regenerate.
// Status: documentation pipeline; nothing here is reviewed or accepted.

package FrontPage {
    doc /* How the repository front page's figures and numbers are built (docs/readme/README.md). */
    action def BuildFrontPage {
        doc /* tools/readme/build_readme.py main(): every figure and number block from the records, then written or checked. */
        action loadStep { doc /* load(): read the records */ }
        action statsStep { doc /* stats(): count the headline numbers */ }
        action bannerStep { doc /* banner.svg */ }
        action glanceStep { doc /* at-a-glance.svg */ }
        action riskmatrixStep { doc /* risk-matrix.svg */ }
        action simulationStep { doc /* simulation.svg */ }
        action roadmapStep { doc /* roadmap.svg */ }
        action taskfiguresStep { doc /* task-*.svg (task_relations.py) */ }
        action blocksStep { doc /* README number blocks */ }
        action applyblocksStep { doc /* write the readme: blocks into README.md */ }
        action decorateStep { doc /* add the terms line (tools.terms) */ }
        action writetextStep { doc /* write, or report stale with --check */ }
        first start then loadStep;
        first loadStep then statsStep;
        first statsStep then bannerStep;
        first bannerStep then glanceStep;
        first glanceStep then riskmatrixStep;
        first riskmatrixStep then simulationStep;
        first simulationStep then roadmapStep;
        first roadmapStep then taskfiguresStep;
        first taskfiguresStep then blocksStep;
        first blocksStep then applyblocksStep;
        first applyblocksStep then decorateStep;
        first decorateStep then writetextStep;
        first writetextStep then done;
    }
}
