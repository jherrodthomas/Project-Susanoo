// CL05Geometry — generated by tools/figures/assets3d_readme.py from the mesh table in docs/3d/assets.
// Do not edit by hand: re-export the geometry (tools/cad/b3d/cl05_web.py) and regenerate.
// Status: CL-05 concept geometry for review, not a design.

package CL05Geometry {
    private import ScalarValues::*;
    doc /* The geometry the general-arrangement sheets load (docs/3d/assets/README.md). */
    part def Mesh {
        attribute partClass : String;
        attribute vertices : Integer;
        attribute triangles : Integer;
    }
    part def Frame {
        attribute label : String;
        attribute movedMeshes : Integer;
        attribute ownMeshes : Integer;
    }
    part def Clip {
        attribute frames : Integer;
        part clipFrame : Frame [*];
    }
    part def GeometryAsset {
        doc /* CL-05 reference layout (build123d, cad/params/CL-05.yaml): concept geometry for review, not a design. In-between frames ease posture parameters; concept kinematics only, no dynamics, balance or load model. */
        attribute units : String;
        attribute quantumMetres : Real;
        attribute kilobytes : Integer;
        part mesh : Mesh [*];
        part clip : Clip [*];
    }
    part susM1 : GeometryAsset {
        attribute :>> units = "metres, z up, x forward";
        attribute :>> quantumMetres = 0.0003;
        attribute :>> kilobytes = 4017;
        part kneelClip :> clip {
            attribute :>> frames = 10;
        }
        part carryClip :> clip {
            attribute :>> frames = 10;
        }
        part egressClip :> clip {
            attribute :>> frames = 1;
        }
        part walkClip :> clip {
            attribute :>> frames = 29;
        }
        part hoseMeshes :> mesh [80] {
            attribute :>> partClass = "hose";
        }
        part armMeshes :> mesh [100] {
            attribute :>> partClass = "arm";
        }
        part structureMeshes :> mesh [25] {
            attribute :>> partClass = "structure";
        }
        part armorMeshes :> mesh [133] {
            attribute :>> partClass = "armor";
        }
        part accessMeshes :> mesh [59] {
            attribute :>> partClass = "access";
        }
        part actuatorMeshes :> mesh [42] {
            attribute :>> partClass = "actuator";
        }
        part seatMeshes :> mesh [5] {
            attribute :>> partClass = "seat";
        }
        part uavMeshes :> mesh [12] {
            attribute :>> partClass = "uav";
        }
        part occupantMeshes :> mesh [9] {
            attribute :>> partClass = "occupant";
        }
        part powerMeshes :> mesh [11] {
            attribute :>> partClass = "power";
        }
        part cageMeshes :> mesh [4] {
            attribute :>> partClass = "cage";
        }
        part dockMeshes :> mesh [7] {
            attribute :>> partClass = "dock";
        }
        part escapeMeshes :> mesh [13] {
            attribute :>> partClass = "escape";
        }
        part safetyMeshes :> mesh [9] {
            attribute :>> partClass = "safety";
        }
        part rotorMeshes :> mesh [4] {
            attribute :>> partClass = "rotor";
        }
        part payloadMeshes :> mesh [1] {
            attribute :>> partClass = "payload";
        }
    }
}
