// Pages3D — generated by tools/figures/pages3d_readme.py from the pages in docs/3d.
// Do not edit by hand: rebuild the pages or change the generator and regenerate.
// Status: concept geometry and synthetic results; no evidence credit.

package Pages3D {
    private import ScalarValues::*;
    doc /* The interactive 3D pages (docs/3d/README.md). */
    part def Page3D {
        doc /* A page in docs/3d: built from the records and results, opened by a CI check. */
        attribute file : String;
        attribute threeVersion : String;
        attribute syntheticLabel : Boolean;
        attribute ciCheck : String;
    }
    part def ScenePage :> Page3D {
        doc /* A replay of one exported scene analysis in one look; a variant changes only the look. */
        attribute scene : String;
        attribute hazards : String;
        attribute outcome : String;
        attribute look : String;
    }
    part def SheetPage :> Page3D {
        doc /* An interactive general-arrangement sheet on the CL-05 concept geometry. */
        attribute sheetNumber : String;
        attribute geometry : String;
        attribute hazardCount : Integer;
        attribute replays : String;
    }
    part def IndexPage :> Page3D {
        doc /* Plain list of the pages. */
        attribute links : Integer;
    }
    part pSusA1 : SheetPage {
        doc /* SUS-A1 on dock and in airspace */
        attribute :>> file = "SUS-A1.html";
        attribute :>> threeVersion = "0.170.0";
        attribute :>> syntheticLabel = true;
        attribute :>> ciCheck = "sim/scenes3d/build_sheet.py --check";
        attribute :>> sheetNumber = "2 of 3";
        attribute :>> geometry = "assets/sus-m1.js";
        attribute :>> hazardCount = 6;
        attribute :>> replays = "SU-01, SU-02, SU-03, SU-04, SU-05, SU-06";
    }
    part pSusM1 : SheetPage {
        doc /* SUS-M1 general arrangement */
        attribute :>> file = "SUS-M1.html";
        attribute :>> threeVersion = "0.170.0";
        attribute :>> syntheticLabel = true;
        attribute :>> ciCheck = "sim/scenes3d/sheet_check.mjs";
        attribute :>> sheetNumber = "1 of 3";
        attribute :>> geometry = "assets/sus-m1.js";
        attribute :>> hazardCount = 22;
        attribute :>> replays = "S3-01, S3-02, S3-03, S3-04";
    }
    part pSusM1Terrain : SheetPage {
        doc /* SUS-M1 terrain course */
        attribute :>> file = "SUS-M1-terrain.html";
        attribute :>> threeVersion = "0.170.0";
        attribute :>> syntheticLabel = true;
        attribute :>> ciCheck = "sim/scenes3d/build_sheet.py --check";
        attribute :>> sheetNumber = "3 of 3";
        attribute :>> geometry = "assets/sus-m1.js, assets/sus-m1-terrain.js, assets/sus-m1-terrain-loaded.js, assets/sus-m1-terrain-physics.js";
        attribute :>> hazardCount = 2;
        attribute :>> replays = "";
    }
    part pS301 : ScenePage {
        doc /* S3-01 Slow supply leak on a slope; balance lost before the hold engages */
        attribute :>> file = "S3-01.html";
        attribute :>> threeVersion = "0.170.0";
        attribute :>> syntheticLabel = true;
        attribute :>> ciCheck = "sim/scenes3d/render.mjs";
        attribute :>> scene = "S3-01";
        attribute :>> hazards = "HAZ-WLK-002";
        attribute :>> outcome = "tip";
        attribute :>> look = "hillside · clear · camera side";
    }
    part pS302 : ScenePage {
        doc /* S3-02 Protective stop removes leg force instead of crouching */
        attribute :>> file = "S3-02.html";
        attribute :>> threeVersion = "0.170.0";
        attribute :>> syntheticLabel = true;
        attribute :>> ciCheck = "sim/scenes3d/render.mjs";
        attribute :>> scene = "S3-02";
        attribute :>> hazards = "HAZ-SAF-001";
        attribute :>> outcome = "hard-drop";
        attribute :>> look = "yard · clear · camera three-quarter";
    }
    part pS303 : ScenePage {
        doc /* S3-03 Frozen posture feedback with no staleness monitor */
        attribute :>> file = "S3-03.html";
        attribute :>> threeVersion = "0.170.0";
        attribute :>> syntheticLabel = true;
        attribute :>> ciCheck = "sim/scenes3d/render.mjs";
        attribute :>> scene = "S3-03";
        attribute :>> hazards = "HAZ-WLK-001";
        attribute :>> outcome = "tip";
        attribute :>> look = "yard · overcast · camera three-quarter";
    }
    part pS304 : ScenePage {
        doc /* S3-04 Burst supply loss with failed load holding; the cockpit drops */
        attribute :>> file = "S3-04.html";
        attribute :>> threeVersion = "0.170.0";
        attribute :>> syntheticLabel = true;
        attribute :>> ciCheck = "sim/scenes3d/render.mjs";
        attribute :>> scene = "S3-04";
        attribute :>> hazards = "HAZ-PIL-002";
        attribute :>> outcome = "hard-drop";
        attribute :>> look = "hillside · clear · camera side";
    }
    part pS305 : ScenePage {
        doc /* S3-05 Link loss with return-to-launch; the UAV descends into the pilot keep-out */
        attribute :>> file = "S3-05.html";
        attribute :>> threeVersion = "0.170.0";
        attribute :>> syntheticLabel = true;
        attribute :>> ciCheck = "sim/scenes3d/render.mjs";
        attribute :>> scene = "S3-05";
        attribute :>> hazards = "HAZ-INT-001";
        attribute :>> outcome = "keepout-breach";
        attribute :>> look = "field · clear · camera overview";
    }
    part pS306 : ScenePage {
        doc /* S3-06 Link loss after the walker moved; the UAV lands at the stale home */
        attribute :>> file = "S3-06.html";
        attribute :>> threeVersion = "0.170.0";
        attribute :>> syntheticLabel = true;
        attribute :>> ciCheck = "sim/scenes3d/render.mjs";
        attribute :>> scene = "S3-06";
        attribute :>> hazards = "HAZ-INT-001, HAZ-DCK-002";
        attribute :>> outcome = "landed-at-stale-home";
        attribute :>> look = "field · clear · camera overview";
    }
    part pS301Dusk : ScenePage {
        doc /* S3-01-dusk Slow supply leak on a slope; balance lost before the hold engages */
        attribute :>> file = "S3-01-dusk.html";
        attribute :>> threeVersion = "0.170.0";
        attribute :>> syntheticLabel = true;
        attribute :>> ciCheck = "sim/scenes3d/render.mjs";
        attribute :>> scene = "S3-01";
        attribute :>> hazards = "HAZ-WLK-002";
        attribute :>> outcome = "tip";
        attribute :>> look = "hillside · dusk · camera side";
    }
    part pS305Fog : ScenePage {
        doc /* S3-05-fog Link loss with return-to-launch; the UAV descends into the pilot keep-out */
        attribute :>> file = "S3-05-fog.html";
        attribute :>> threeVersion = "0.170.0";
        attribute :>> syntheticLabel = true;
        attribute :>> ciCheck = "sim/scenes3d/render.mjs";
        attribute :>> scene = "S3-05";
        attribute :>> hazards = "HAZ-INT-001";
        attribute :>> outcome = "keepout-breach";
        attribute :>> look = "field · fog · camera overview";
    }
    part pIndex : IndexPage {
        doc /* Susanoo 3D scenes */
        attribute :>> file = "index.html";
        attribute :>> threeVersion = "";
        attribute :>> syntheticLabel = true;
        attribute :>> ciCheck = "sim/scenes3d/build_pages.py --check";
        attribute :>> links = 11;
    }
}
