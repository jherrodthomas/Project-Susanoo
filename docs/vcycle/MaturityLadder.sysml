// MaturityLadder — generated by tools/figures/vcycle_readme.py from the ladder in tools/vcycle/build_vcycle.py.
// Do not edit by hand: change the generator's ladder and regenerate.
// Status: orientation only; maturity is computed from record status, nothing is reviewed or accepted.

package VCycleMaturity {
    doc /* Record maturity on the System V cycle page (docs/vcycle/README.md). */
    attribute def AuthorOrAiI0;
    attribute def DesignOwnerAfterReview;
    attribute def HumanReviewerI1OrHigher;
    attribute def LeadThroughAReviewRecordR13;
    attribute def NamedHumanReviewerInRoleR13;
    attribute def RiskAcceptanceAuthority;
    state def MaturityLadder {
        doc /* Rungs of record maturity on the System V cycle page; the trigger is who may move a record up. Computed from record status for orientation only (rule R13). */
        entry; then NotStarted;
        state NotStarted { doc /* No record yet. Now: 2 records. */ }
        state Draft { doc /* open, draft, candidate, in-work. Now: 47 records. */ }
        state Reviewed { doc /* Review record by a named human. */ }
        state Baselined { doc /* Requirement baselined, task approved. */ }
        state Implemented { doc /* Built or configured item under control. */ }
        state Verified { doc /* Evidence accepted; hazard verified. */ }
        state Validated { doc /* Meets intended use; risk accepted. */ }
        transition t1 first NotStarted accept AuthorOrAiI0 then Draft;
        transition t2 first Draft accept HumanReviewerI1OrHigher then Reviewed;
        transition t3 first Reviewed accept LeadThroughAReviewRecordR13 then Baselined;
        transition t4 first Baselined accept DesignOwnerAfterReview then Implemented;
        transition t5 first Implemented accept NamedHumanReviewerInRoleR13 then Verified;
        transition t6 first Verified accept RiskAcceptanceAuthority then Validated;
    }
}
