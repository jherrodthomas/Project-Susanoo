// ProjectLifecycle — generated by tools/figures/framework_readme.py from the gates in standards/tailoring/mil-std-882e.yaml.
// Do not edit by hand: change the tailoring or the generator and regenerate.
// Status: project-defined gates; no gate has passed.

package ProjectLifecycle {
    doc /* Lifecycle gates of framework/lifecycle.md (gate passes need a named human review, rule R13). */
    attribute def ChangeNeedsANewRelease;
    attribute def GatePassedNamedReview;
    attribute def Released;
    state def GateLifecycle {
        doc /* Project-defined gates of framework/lifecycle.md, in order, as mapped in the 882E tailoring. */
        entry; then G0;
        state G0 { doc /* Concept (phase MSA) */ }
        state G1 { doc /* Requirements (phase MSA) */ }
        state G2 { doc /* Preliminary architecture (phase TD) */ }
        state G3 { doc /* Detailed design (phase EMD) */ }
        state G4 { doc /* Bench and simulation readiness (phase EMD) */ }
        state G5 { doc /* Verification and assessment (phase EMD) */ }
        state G6 { doc /* Release (phase PD) */ }
        state G7 { doc /* Change and sustainment (phase OS) */ }
        transition t1 first G0 accept GatePassedNamedReview then G1;
        transition t2 first G1 accept GatePassedNamedReview then G2;
        transition t3 first G2 accept GatePassedNamedReview then G3;
        transition t4 first G3 accept GatePassedNamedReview then G4;
        transition t5 first G4 accept GatePassedNamedReview then G5;
        transition t6 first G5 accept GatePassedNamedReview then G6;
        transition t7 first G6 accept Released then G7;
        transition t8 first G7 accept ChangeNeedsANewRelease then G6;
    }
}
