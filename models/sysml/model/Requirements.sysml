// GENERATED by tools/sysml/gen_requirements.py from requirements/SYS-*.yaml. Do not edit;
// edit the requirement records and re-run.

package SusanooRequirements {
    private import SusanooLibrary::*;

    requirement <'SYS-001'> pilotReadinessActuationInterlock : SystemRequirement {
        doc /* The system shall inhibit leg actuation until pilot station readiness conditions (restraint fastened, hatch secured, controls neutral, exclusion zone confirmed) are satisfied. */
        @Source { record = "requirements/SYS-001.yaml"; }
        @HazardRef { ids = ("HAZ-PIL-001"); }
    }
    requirement <'SYS-002'> operatorProtectiveStop : SystemRequirement {
        doc /* The system shall provide an operator-requested protective stop with a defined, analyzed safe behavior for each operating mode that does not depend on instant zero torque. */
        @Source { record = "requirements/SYS-002.yaml"; }
        @HazardRef { ids = ("HAZ-SAF-001"); }
    }
    requirement <'SYS-003'> dockedRotorInhibit : SystemRequirement {
        doc /* The UAV shall be prevented from rotor startup while mechanically retained, except under an approved maintenance procedure. */
        @Source { record = "requirements/SYS-003.yaml"; }
        @HazardRef { ids = ("HAZ-DCK-001"); }
    }
    requirement <'SYS-004'> feedbackFaultDetection : SystemRequirement {
        doc /* The system shall detect loss or staleness of essential actuator and posture feedback and transition to a documented degraded state. */
        @Source { record = "requirements/SYS-004.yaml"; }
        @HazardRef { ids = ("HAZ-WLK-001"); }
    }
    requirement <'SYS-005'> positiveDockingRetentionState : SystemRequirement {
        doc /* The docking interface shall report a positively confirmed retained/unretained state derived from independent sensing. */
        @Source { record = "requirements/SYS-005.yaml"; }
        @HazardRef { ids = ("HAZ-DCK-002"); }
    }
    requirement <'SYS-006'> launchAndRecoveryEnvelopeInhibit : SystemRequirement {
        doc /* UAV launch and recovery shall be inhibited outside a verified operational envelope of walker posture, motion and dock state. */
        @Source { record = "requirements/SYS-006.yaml"; }
        @HazardRef { ids = ("HAZ-INT-001", "HAZ-DCK-004"); }
    }
    requirement <'SYS-007'> storedHydraulicEnergyIsolation : SystemRequirement {
        doc /* The walker shall provide lockable isolation and verifiable dissipation of stored hydraulic pressure before maintenance access. */
        @Source { record = "requirements/SYS-007.yaml"; }
        @HazardRef { ids = ("HAZ-PWR-001"); }
    }
    requirement <'SYS-008'> stabilityEnvelopeProtection : SystemRequirement {
        doc /* The walker shall limit commanded motion and payload to a verified static and dynamic stability envelope, including a terrain slope limit of 20 degrees with the centre of mass no more than 0.12 m ahead of the stance foot, and provide pilot protection in a fall or overturn. */
        @Source { record = "requirements/SYS-008.yaml"; }
        @HazardRef { ids = ("HAZ-WLK-002"); }
    }
    requirement <'SYS-009'> failSafeLoadHolding : SystemRequirement {
        doc /* The walker shall hold its posture without supply or command on loss of actuator supply, with load holding engaging in less than the free-fall time from the highest operating posture. */
        @Source { record = "requirements/SYS-009.yaml"; }
        @HazardRef { ids = ("HAZ-PIL-002"); }
    }
    requirement <'SYS-010'> protectiveStopIndependence : SystemRequirement {
        doc /* The protective stop path shall achieve its defined safe behavior without depending on the mission, motion and balance control software. */
        @Source { record = "requirements/SYS-010.yaml"; }
        @HazardRef { ids = ("HAZ-SAF-001"); }
    }
    requirement <'SYS-011'> protectiveStopReactionTime : SystemRequirement {
        doc /* The protective stop shall begin its defined safe behavior within the reaction time allocated by hazard analysis for each operating mode. */
        @Source { record = "requirements/SYS-011.yaml"; }
        @HazardRef { ids = ("HAZ-SAF-001"); }
    }
    requirement <'SYS-012'> rotorArmingRequiresConfirmedRelease : SystemRequirement {
        doc /* UAV rotor arming shall require a positively confirmed unretained dock state reported over the docking interface. */
        @Source { record = "requirements/SYS-012.yaml"; }
        @HazardRef { ids = ("HAZ-DCK-001"); }
    }
    requirement <'SYS-013'> uavLinkLossContingencyLandsClearOfTheWalker : SystemRequirement {
        doc /* On loss of the integration link the UAV shall hold for a set time and then land in place, and shall not return to the dock or descend within the pilot keep-out without a recovery permit from the integration manager. */
        @Source { record = "requirements/SYS-013.yaml"; }
        @HazardRef { ids = ("HAZ-INT-001"); }
    }
    requirement <'SYS-014'> independentTractionBatteryIsolation : SystemRequirement {
        doc /* If the series-hybrid power alternative is retained, the walker shall isolate the traction battery on cell over-temperature, over-voltage or over-current independently of the motion controller, and warn the pilot. */
        @Source { record = "requirements/SYS-014.yaml"; }
        @HazardRef { ids = ("HAZ-PWR-002"); }
    }
    requirement <'SYS-015'> fuelShutOffOnProtectiveStop : SystemRequirement {
        doc /* If the series-hybrid power alternative is retained, a protective stop or detected fall shall shut off fuel to the engine-generator and stop the engine. */
        @Source { record = "requirements/SYS-015.yaml"; }
        @HazardRef { ids = ("HAZ-PWR-003"); }
    }
    requirement <'SYS-016'> actuatorTorqueReserveAgainstSupplyLoss : SystemRequirement {
        doc /* Each ankle actuator shall deliver at least 1.5 m g L_foot of torque at full actuator supply and at least 0.6 m g L_foot at the supply at which load holding engages, and each knee actuator at least 26.5 kN m at full supply (SPEC-WLK-001 mass and geometry, the reference layout CL-05), so that a loss of supply inside the operating envelope does not tip the walker before load holding engages. */
        @Source { record = "requirements/SYS-016.yaml"; }
        @HazardRef { ids = ("HAZ-WLK-002"); }
    }
    requirement <'SYS-017'> armStowInterlockForWalking : SystemRequirement {
        doc /* The walker shall inhibit walking until both manipulator arms are confirmed stowed and locked, or locked in the carry pose under the loaded-walking conditions of SYS-019, shall hold the arms in that pose until walking has stopped, and shall inhibit manipulation while the exclusion zone around the arms' reach is not confirmed clear. */
        @Source { record = "requirements/SYS-017.yaml"; }
        @HazardRef { ids = ("HAZ-MAN-001", "HAZ-MAN-002"); }
    }
    requirement <'SYS-018'> controlledLoweredPostureForIngressAndEgress : SystemRequirement {
        doc /* The walker shall provide a controlled lowered posture for ingress and egress, with the cockpit floor at or below a defined height, entered and left at a controlled speed only while the area under and around the pod and legs is confirmed clear, and shall inhibit walking while an access ladder is deployed. */
        @Source { record = "requirements/SYS-018.yaml"; }
        @HazardRef { ids = ("HAZ-WLK-003", "HAZ-PIL-001", "HAZ-PIL-004", "HAZ-PIL-005"); }
    }
    requirement <'SYS-019'> loadedWalkingLimits : SystemRequirement {
        doc /* The walker shall permit walking with a payload only while the payload is confirmed secured, both arms are locked in a defined carry pose and payload mass and centre of gravity are within defined limits, and shall then limit walking speed, step height and terrain slope to defined loaded values inside the stability envelope of SYS-008. */
        @Source { record = "requirements/SYS-019.yaml"; }
        @HazardRef { ids = ("HAZ-MAN-002", "HAZ-WLK-002"); }
    }
    requirement <'SYS-020'> emergencyEgressWithoutPowerOrKneeling : SystemRequirement {
        doc /* The pilot shall be able to leave the walker from the standing posture without platform power and without kneeling, through an exit other than the front opening, with a descent aid and handholds that keep three points of contact to the ground. */
        @Source { record = "requirements/SYS-020.yaml"; }
        @HazardRef { ids = ("HAZ-PIL-003", "HAZ-PIL-004"); }
    }
    requirement <'SYS-021'> uavDataValidityAndStalenessAnnunciation : SystemRequirement {
        doc /* The pilot display shall mark UAV imagery, position and telemetry as not valid when they fail validity checks, and as not current when they have not updated within a defined time, so that they are never shown as current and valid when they are not. */
        @Source { record = "requirements/SYS-021.yaml"; }
        @HazardRef { ids = ("HAZ-INT-002"); }
    }
    requirement <'SYS-022'> dockChargingProtectionAndIsolation : SystemRequirement {
        doc /* The dock shall charge the UAV battery only when the aircraft is seated and confirmed, shall stop charging on over-voltage, over-current or over-temperature independently of the charging software, and shall keep its charging contacts de-energised and shrouded whenever no UAV is seated or charging has been isolated for handling. */
        @Source { record = "requirements/SYS-022.yaml"; }
        @HazardRef { ids = ("HAZ-DCK-003", "HAZ-DCK-004"); }
    }
    requirement <'SYS-023'> maintenanceAccessAtHeight : SystemRequirement {
        doc /* Maintenance tasks on the walker above a defined working height shall be done from a guarded access platform or stand, or, where no platform can reach, with fall arrest attached to rated anchor points provided on the walker. */
        @Source { record = "requirements/SYS-023.yaml"; }
        @HazardRef { ids = ("HAZ-GSE-001"); }
    }
    requirement <'SYS-024'> externalExtractionOfAnIncapacitatedPilot : SystemRequirement {
        doc /* Trained crew shall be able to release the hatch and the pilot restraint from outside the walker without platform power, and to remove an incapacitated pilot from a standing, kneeling or fallen walker within a defined time, with fall protection for the rescuers. */
        @Source { record = "requirements/SYS-024.yaml"; }
        @HazardRef { ids = ("HAZ-PIL-006"); }
    }
}
