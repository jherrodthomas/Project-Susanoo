// GENERATED by tools/sysml/gen_requirements.py from requirements/SYS-*.yaml. Do not edit;
// edit the requirement records and re-run.

package SusanooSatisfaction {
    private import SusanooRequirements::*;
    private import SusanooArchitecture::*;

    satisfy 'SYS-001' by context.system.walker.safetyMonitor;
    satisfy 'SYS-001' by context.system.walker.pilotStation;
    satisfy 'SYS-002' by context.system.walker.safetyMonitor;
    satisfy 'SYS-003' by context.system.walker.dock;
    satisfy 'SYS-003' by context.system.uav;
    satisfy 'SYS-004' by context.system.walker.legs;
    satisfy 'SYS-004' by context.system.walker.safetyMonitor;
    satisfy 'SYS-005' by context.system.walker.dock;
    satisfy 'SYS-006' by context.system.walker.dock;
    satisfy 'SYS-006' by context.system.uav;
    satisfy 'SYS-007' by context.system.walker.power;
    satisfy 'SYS-007' by context.system.groundSupport;
    satisfy 'SYS-008' by context.system.walker.legs;
    satisfy 'SYS-008' by context.system.walker.pilotStation;
    satisfy 'SYS-009' by context.system.walker.legs;
    satisfy 'SYS-009' by context.system.walker.power;
    satisfy 'SYS-010' by context.system.walker.safetyMonitor;
    satisfy 'SYS-011' by context.system.walker.safetyMonitor;
    satisfy 'SYS-012' by context.system.walker.dock;
    satisfy 'SYS-012' by context.system.integrationManager;
    satisfy 'SYS-013' by context.system.uav;
    satisfy 'SYS-013' by context.system.integrationManager;
    satisfy 'SYS-014' by context.system.walker.power.battery;
    satisfy 'SYS-014' by context.system.walker.safetyMonitor;
    satisfy 'SYS-015' by context.system.walker.power.engineGenerator;
    satisfy 'SYS-015' by context.system.walker.safetyMonitor;
    satisfy 'SYS-016' by context.system.walker.legs;
    satisfy 'SYS-017' by context.system.walker.manipulators;
    satisfy 'SYS-017' by context.system.walker.motionControl;
    satisfy 'SYS-017' by context.system.walker.safetyMonitor;
    satisfy 'SYS-018' by context.system.walker.legs;
    satisfy 'SYS-018' by context.system.walker.pilotStation;
    satisfy 'SYS-018' by context.system.walker.safetyMonitor;
    satisfy 'SYS-019' by context.system.walker.manipulators;
    satisfy 'SYS-019' by context.system.walker.legs;
    satisfy 'SYS-019' by context.system.walker.motionControl;
    satisfy 'SYS-019' by context.system.walker.safetyMonitor;
    satisfy 'SYS-020' by context.system.walker.pilotStation;
    satisfy 'SYS-020' by context.system.walker.safetyMonitor;
    satisfy 'SYS-021' by context.system.integrationManager;
    satisfy 'SYS-021' by context.system.walker.pilotStation;
    satisfy 'SYS-022' by context.system.walker.dock;
    satisfy 'SYS-022' by context.system.uav;
    satisfy 'SYS-023' by context.system.groundSupport;
    satisfy 'SYS-023' by context.system.walker.legs;
    satisfy 'SYS-024' by context.system.walker.pilotStation;
    satisfy 'SYS-024' by context.system.walker.safetyMonitor;
}
