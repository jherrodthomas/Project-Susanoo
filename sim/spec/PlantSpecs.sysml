// PlantSpecs — generated by tools/figures/spec_readme.py from sim/spec/*.yaml and sim/plant/spec.py.
// Do not edit by hand: change the specs or the generator and regenerate.
// Status: concept assumptions, not design values.

package PlantSpecs {
    private import ScalarValues::*;
    doc /* Walker parameter specs for the level-1 and level-2 models (sim/spec/README.md). */
    enum def ParamStatus {
        doc /* The statuses sim/plant/spec.py accepts. */
        enum 'assumed';
        enum 'derived';
        enum 'published';
    }
    part def SpecParameter {
        doc /* One plant parameter; spec.py refuses it without every field or outside its range. */
        attribute value : Real;
        attribute unit : String;
        attribute rangeLow : Real;
        attribute rangeHigh : Real;
        attribute status : ParamStatus;
        attribute source : String;
    }
    part def ParameterSpec {
        attribute specId : String;
        attribute revision : String;
        part parameters : SpecParameter[*];
    }
    part walkerSpec : ParameterSpec {
        doc /* sim/spec/walker.yaml: 24 parameters */
        attribute :>> specId = "SPEC-WLK-001";
        attribute :>> revision = "0.1-draft";
    }
    part walkerL2Spec : ParameterSpec {
        doc /* sim/spec/walker_l2.yaml: 24 parameters */
        attribute :>> specId = "SPEC-WLK-L2-001";
        attribute :>> revision = "0.1-draft";
    }
}
