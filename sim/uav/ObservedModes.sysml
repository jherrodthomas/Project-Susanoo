// ObservedModes — generated by tools/figures/uav_readme.py from the committed PX4 SITL results (sim/results/uav).
// Do not edit by hand: re-run the harness or change the generator and regenerate.
// Status: observed behaviour of PX4 in synthetic runs; no evidence credit.

package ObservedModes {
    doc /* PX4 flight modes seen in the SUS-A1 failsafe scenarios (sim/uav/README.md). */
    attribute def SeenInSu01Su02;
    attribute def SeenInSu03Su04Su06;
    attribute def SeenInSu06;
    state def Px4FailsafeModes {
        doc /* PX4 flight modes and the changes between them seen in the committed SITL runs after the injection. */
        entry; then AutoLoiter;
        state AutoLand { doc /* AUTO.LAND */ }
        state AutoLoiter { doc /* AUTO.LOITER */ }
        state AutoRtl { doc /* AUTO.RTL */ }
        transition t1 first AutoLand accept SeenInSu06 then AutoLoiter;
        transition t2 first AutoLoiter accept SeenInSu03Su04Su06 then AutoLand;
        transition t3 first AutoLoiter accept SeenInSu01Su02 then AutoRtl;
    }
}
