// WalkerL2 — generated by tools/figures/mujoco_readme.py from sim/spec/walker_l2.yaml.
// Do not edit by hand: change the spec or the generator and regenerate.
// Status: level-2 concept assumptions; synthetic, no evidence credit.

package WalkerL2 {
    private import ScalarValues::*;
    doc /* The level-2 MuJoCo walker model (sim/mujoco/README.md). */
    part def Torso {
        doc /* Cockpit, pelvis, power and manipulators lumped above the hips; slide x, slide z and pitch. */
        attribute torsoMassKg : Real = 3473.8;  // kg, derived
        attribute hipHeightM : Real = 2.34;  // m, derived
        attribute torsoComAboveHipM : Real = 0.748;  // m, derived
    }
    part def Leg {
        doc /* Hip, knee and ankle hinges about y and a box foot; each joint has a lock for load holding. */
        attribute thighLengthM : Real = 1.0;  // m, derived
        attribute shankLengthM : Real = 1.05;  // m, derived
        attribute ankleHeightM : Real = 0.55;  // m, derived
        attribute hipTorqueMaxNm : Real = 40000.0;  // N m, assumed
        attribute kneeTorqueMaxNm : Real = 26500.0;  // N m, derived
        attribute ankleTorqueMaxNm : Real = 40500.0;  // N m, derived
    }
    part def WalkerL2 {
        doc /* SPEC-WLK-L2-001 0.1-draft: the planar level-2 walker in MuJoCo. */
        attribute timestepS : Real = 0.002;  // s, assumed
        attribute groundFriction : Real = 1.0;  // -, assumed
        part torso : Torso;
        part leftLeg : Leg;
        part rightLeg : Leg;
    }
}
