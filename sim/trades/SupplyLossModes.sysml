// SupplyLossModes — generated by tools/figures/trades_readme.py from sim/trades/fault_response.yaml and sim/spec/walker.yaml.
// Do not edit by hand: change the evidence definition or the generator and regenerate.
// Status: trade-study evidence input; synthetic, no evidence credit.

package SupplyLossModes {
    private import ScalarValues::*;
    doc /* Supply-loss modes of the TS-001 alternatives (sim/trades/README.md). */
    part def SupplyLossMode {
        doc /* How joint torque falls when supply is lost: the only way the alternatives differ at simulation fidelity. */
        attribute actuationVariant : String;
        attribute fault : String;
        attribute torqueFloor : Real;  // fraction of full torque left after the fault
        attribute alternatives : String;
    }
    part aloss : SupplyLossMode {
        doc /* A-LOSS: Hydraulic supply lost (line burst to slow leak); torque falls to zero on every joint */
        attribute :>> actuationVariant = "hydraulic";
        attribute :>> fault = "FLT-01";
        attribute :>> torqueFloor = 0.0;
        attribute :>> alternatives = "A";
    }
    part bsag : SupplyLossMode {
        doc /* B-SAG: Bus undervoltage (generator lost, battery sags); torque falls to the residual floor */
        attribute :>> actuationVariant = "electric";
        attribute :>> fault = "FLT-04";
        attribute :>> torqueFloor = 0.35;
        attribute :>> alternatives = "B-EHA, B-EMA";
    }
    part bisol : SupplyLossMode {
        doc /* B-ISOL: Battery isolated (contactor opens, SYS-014) with the generator lost; torque falls to zero */
        attribute :>> actuationVariant = "electric";
        attribute :>> fault = "FLT-04";
        attribute :>> torqueFloor = 0.0;
        attribute :>> alternatives = "B-EHA, B-EMA";
    }
}
