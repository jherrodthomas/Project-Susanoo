// ResultSets — generated by tools/figures/results_readme.py from the committed results in sim/results.
// Do not edit by hand: re-run the simulations or change the generator and regenerate.
// Status: synthetic results; no evidence credit.

package ResultSets {
    private import ScalarValues::*;
    doc /* The committed simulation results (sim/results/README.md). */
    part def ResultSet {
        doc /* A committed simulation result: synthetic, no evidence credit, re-run and compared in CI. */
        attribute dataKind : String;
        attribute evidenceCredit : Boolean;
        attribute specDigest : String;
        attribute writer : String;
        attribute ciCheck : String;
    }
    part l2Crosscheck : ResultSet {
        doc /* sim/results/l2-crosscheck.json */
        attribute :>> dataKind = "synthetic";
        attribute :>> evidenceCredit = false;
        attribute :>> specDigest = "ce8f2beafd0f";
        attribute :>> writer = "sim.mujoco.crosscheck";
        attribute :>> ciCheck = "--compare";
    }
    part l2Terrain : ResultSet {
        doc /* sim/results/l2-terrain.json */
        attribute :>> dataKind = "synthetic";
        attribute :>> evidenceCredit = false;
        attribute :>> specDigest = "";
        attribute :>> writer = "sim.mujoco.terrain";
        attribute :>> ciCheck = "--check";
    }
    part plantResults : ResultSet {
        doc /* sim/results/plant-results.json */
        attribute :>> dataKind = "synthetic";
        attribute :>> evidenceCredit = false;
        attribute :>> specDigest = "ce8f2beafd0f";
        attribute :>> writer = "sim.plant.report";
        attribute :>> ciCheck = "--check";
    }
    part searchSf01 : ResultSet {
        doc /* sim/results/search-SF-01.json */
        attribute :>> dataKind = "synthetic";
        attribute :>> evidenceCredit = false;
        attribute :>> specDigest = "ce8f2beafd0f";
        attribute :>> writer = "sim.search.search";
        attribute :>> ciCheck = "--check";
    }
    part sizingCf4 : ResultSet {
        doc /* sim/results/sizing-cf4.json */
        attribute :>> dataKind = "synthetic";
        attribute :>> evidenceCredit = false;
        attribute :>> specDigest = "ce8f2beafd0f";
        attribute :>> writer = "sim.mujoco.sizing";
        attribute :>> ciCheck = "--compare";
    }
    part ts001FaultResponse : ResultSet {
        doc /* sim/results/ts001-fault-response.json */
        attribute :>> dataKind = "synthetic";
        attribute :>> evidenceCredit = false;
        attribute :>> specDigest = "ce8f2beafd0f";
        attribute :>> writer = "sim.trades.fault_response";
        attribute :>> ciCheck = "--compare";
    }
}
