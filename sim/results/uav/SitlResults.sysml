// SitlResults — generated by tools/figures/uavresults_readme.py from sim/uav/harness.py score().
// Do not edit by hand: change the harness or the generator and regenerate.
// Status: synthetic simulation output; no evidence credit.

package SitlResults {
    doc /* How a PX4 SITL run's outcome is decided (sim/results/uav/README.md). */
    action def ClassifyOutcome {
        doc /* How sim/uav/harness.py score() decides a run's outcome: the first test that holds, in this order. */
        action isKeepoutBreach { doc /* keepout-breach: below the keep-out altitude, closer to the pilot than pilot_keepout_m */ }
        action isLandedAtStaleHome { doc /* landed-at-stale-home: landed (PX4 disarmed), and landing point more than 5.0 m from the dock and the walker moved */ }
        action isGeofenceOvershoot { doc /* geofence-overshoot: farthest point beyond geofence_radius_m + 2.0 m */ }
        action isLandedClear { doc /* landed-clear: landed (PX4 disarmed) */ }
        action isContained { doc /* contained: the injection is reposition_beyond_fence_at_s */ }
        action isAirborneAtHorizon { doc /* airborne-at-horizon: otherwise */ }
        first start then isKeepoutBreach;
        first isKeepoutBreach then isLandedAtStaleHome;
        first isLandedAtStaleHome then isGeofenceOvershoot;
        first isGeofenceOvershoot then isLandedClear;
        first isLandedClear then isContained;
        first isContained then isAirborneAtHorizon;
        first isAirborneAtHorizon then done;
    }
}
