// Scenes3D — generated by tools/figures/scenes3d_readme.py from sim/scenes3d/scenes.yaml and the exported analysis.
// Do not edit by hand: change the scenes or the generator and regenerate.
// Status: pictures of synthetic simulation output; no evidence credit.

package Scenes3D {
    private import ScalarValues::*;
    doc /* The 3D hazard scenes (sim/scenes3d/README.md). */
    enum def MotionSource {
        doc /* Where a scene's motion comes from. */
        enum 'edge';
        enum 'plant';
        enum 'sitl';
    }
    part def Analysis {
        doc /* The exported analysis (sim/scenes3d/out): read only from the scene's motion block and the records it names. */
        attribute source : MotionSource;
        attribute reference : String;
        attribute outcome : String;
        attribute specDigest : String;
    }
    part def Look {
        doc /* Picture only: environment, condition and camera. Never read by export_scene.py. */
        attribute environment : String;
        attribute condition : String;
        attribute camera : String;
    }
    part def Scene3D {
        attribute hazards : String;
        part motionAnalysis : Analysis;
        part look : Look;
    }
    part s01 : Scene3D {
        doc /* S3-01: Slow supply leak on a slope; balance lost before the hold engages */
        attribute :>> hazards = "HAZ-WLK-002";
        part :>> motionAnalysis {
            attribute :>> source = MotionSource::'edge';
            attribute :>> reference = "SF-01 EC-08";
            attribute :>> outcome = "tip";
        }
        part :>> look {
            attribute :>> environment = "hillside";
            attribute :>> condition = "clear";
            attribute :>> camera = "side";
        }
    }
    part s01dusk : Scene3D {
        doc /* S3-01-dusk: Slow supply leak on a slope; balance lost before the hold engages */
        attribute :>> hazards = "HAZ-WLK-002";
        part :>> motionAnalysis {
            attribute :>> source = MotionSource::'edge';
            attribute :>> reference = "SF-01 EC-08";
            attribute :>> outcome = "tip";
        }
        part :>> look {
            attribute :>> environment = "hillside";
            attribute :>> condition = "dusk";
            attribute :>> camera = "side";
        }
    }
    part s02 : Scene3D {
        doc /* S3-02: Protective stop removes leg force instead of crouching */
        attribute :>> hazards = "HAZ-SAF-001";
        part :>> motionAnalysis {
            attribute :>> source = MotionSource::'plant';
            attribute :>> reference = "fault FLT-03";
            attribute :>> outcome = "hard-drop";
        }
        part :>> look {
            attribute :>> environment = "yard";
            attribute :>> condition = "clear";
            attribute :>> camera = "three-quarter";
        }
    }
    part s03 : Scene3D {
        doc /* S3-03: Frozen posture feedback with no staleness monitor */
        attribute :>> hazards = "HAZ-WLK-001";
        part :>> motionAnalysis {
            attribute :>> source = MotionSource::'plant';
            attribute :>> reference = "fault FLT-02";
            attribute :>> outcome = "tip";
        }
        part :>> look {
            attribute :>> environment = "yard";
            attribute :>> condition = "overcast";
            attribute :>> camera = "three-quarter";
        }
    }
    part s04 : Scene3D {
        doc /* S3-04: Burst supply loss with failed load holding; the cockpit drops */
        attribute :>> hazards = "HAZ-PIL-002";
        part :>> motionAnalysis {
            attribute :>> source = MotionSource::'edge';
            attribute :>> reference = "SF-01 EC-01";
            attribute :>> outcome = "hard-drop";
        }
        part :>> look {
            attribute :>> environment = "hillside";
            attribute :>> condition = "clear";
            attribute :>> camera = "side";
        }
    }
    part s05 : Scene3D {
        doc /* S3-05: Link loss with return-to-launch; the UAV descends into the pilot keep-out */
        attribute :>> hazards = "HAZ-INT-001";
        part :>> motionAnalysis {
            attribute :>> source = MotionSource::'sitl';
            attribute :>> reference = "SU-01";
            attribute :>> outcome = "keepout-breach";
        }
        part :>> look {
            attribute :>> environment = "field";
            attribute :>> condition = "clear";
            attribute :>> camera = "overview";
        }
    }
    part s05fog : Scene3D {
        doc /* S3-05-fog: Link loss with return-to-launch; the UAV descends into the pilot keep-out */
        attribute :>> hazards = "HAZ-INT-001";
        part :>> motionAnalysis {
            attribute :>> source = MotionSource::'sitl';
            attribute :>> reference = "SU-01";
            attribute :>> outcome = "keepout-breach";
        }
        part :>> look {
            attribute :>> environment = "field";
            attribute :>> condition = "fog";
            attribute :>> camera = "overview";
        }
    }
    part s06 : Scene3D {
        doc /* S3-06: Link loss after the walker moved; the UAV lands at the stale home */
        attribute :>> hazards = "HAZ-INT-001, HAZ-DCK-002";
        part :>> motionAnalysis {
            attribute :>> source = MotionSource::'sitl';
            attribute :>> reference = "SU-02";
            attribute :>> outcome = "landed-at-stale-home";
        }
        part :>> look {
            attribute :>> environment = "field";
            attribute :>> condition = "clear";
            attribute :>> camera = "overview";
        }
    }
}
