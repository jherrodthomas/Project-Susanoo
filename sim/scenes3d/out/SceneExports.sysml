// SceneExports — generated by tools/figures/sceneout_readme.py from sim/scenes3d/out.
// Do not edit by hand: change the scenes or the generator and regenerate.
// Status: synthetic simulation output; design aid only, no evidence credit.

package SceneExports {
    private import ScalarValues::*;
    doc /* The exported analysis of every 3D scene (sim/scenes3d/out/README.md). */
    part def SceneExport {
        doc /* The exported analysis of one 3D scene (sim/scenes3d/export_scene.py). Synthetic. */
        attribute sceneId : String;
        attribute hazards : String [1..*];
        attribute source : String;
        attribute reference : String;
        attribute evidenceCredit : Boolean = false;
    }
    part def Run {
        doc /* One walker run from sim/plant/walker.py, downsampled to 10 Hz. */
        attribute outcome : String;
        attribute mishapTime : Real [0..1];
        attribute frameCount : Integer;
    }
    part def WalkerExport :> SceneExport {
        attribute slopeDeg : Real;
        attribute specDigest : String;
        part performed : Run;
        part intended : Run;
    }
    part def UavExport :> SceneExport {
        attribute px4 : String;
        attribute outcome : String;
        attribute keepoutMetres : Real;
        attribute keepoutAltMetres : Real;
        attribute minPilotDistanceLowMetres : Real;
        attribute walkerMoved : Boolean;
    }
    part exportS301 : WalkerExport {
        attribute :>> sceneId = "S3-01";
        attribute :>> hazards = ("HAZ-WLK-002");
        attribute :>> source = "edge";
        attribute :>> reference = "SF-01 EC-08";
        attribute :>> slopeDeg = 19.5;
        attribute :>> specDigest = "ce8f2beafd0f";
        part :>> performed {
            attribute :>> outcome = "tip";
            attribute :>> mishapTime = 3.56;
            attribute :>> frameCount = 37;
        }
        part :>> intended {
            attribute :>> outcome = "safe";
            attribute :>> frameCount = 61;
        }
    }
    part exportS302 : WalkerExport {
        attribute :>> sceneId = "S3-02";
        attribute :>> hazards = ("HAZ-SAF-001");
        attribute :>> source = "plant";
        attribute :>> reference = "fault FLT-03";
        attribute :>> slopeDeg = 0.0;
        attribute :>> specDigest = "ce8f2beafd0f";
        part :>> performed {
            attribute :>> outcome = "hard-drop";
            attribute :>> mishapTime = 1.495;
            attribute :>> frameCount = 16;
        }
        part :>> intended {
            attribute :>> outcome = "safe";
            attribute :>> frameCount = 61;
        }
    }
    part exportS303 : WalkerExport {
        attribute :>> sceneId = "S3-03";
        attribute :>> hazards = ("HAZ-WLK-001");
        attribute :>> source = "plant";
        attribute :>> reference = "fault FLT-02";
        attribute :>> slopeDeg = 0.0;
        attribute :>> specDigest = "ce8f2beafd0f";
        part :>> performed {
            attribute :>> outcome = "tip";
            attribute :>> mishapTime = 2.77;
            attribute :>> frameCount = 29;
        }
        part :>> intended {
            attribute :>> outcome = "safe";
            attribute :>> frameCount = 61;
        }
    }
    part exportS304 : WalkerExport {
        attribute :>> sceneId = "S3-04";
        attribute :>> hazards = ("HAZ-PIL-002");
        attribute :>> source = "edge";
        attribute :>> reference = "SF-01 EC-01";
        attribute :>> slopeDeg = 12.0;
        attribute :>> specDigest = "ce8f2beafd0f";
        part :>> performed {
            attribute :>> outcome = "hard-drop";
            attribute :>> mishapTime = 1.58;
            attribute :>> frameCount = 17;
        }
        part :>> intended {
            attribute :>> outcome = "safe";
            attribute :>> frameCount = 61;
        }
    }
    part exportS305 : UavExport {
        attribute :>> sceneId = "S3-05";
        attribute :>> hazards = ("HAZ-INT-001");
        attribute :>> source = "sitl";
        attribute :>> reference = "SU-01";
        attribute :>> px4 = "v1.16.2";
        attribute :>> outcome = "keepout-breach";
        attribute :>> keepoutMetres = 3.0;
        attribute :>> keepoutAltMetres = 8.0;
        attribute :>> minPilotDistanceLowMetres = 1.85;
        attribute :>> walkerMoved = false;
    }
    part exportS306 : UavExport {
        attribute :>> sceneId = "S3-06";
        attribute :>> hazards = ("HAZ-INT-001", "HAZ-DCK-002");
        attribute :>> source = "sitl";
        attribute :>> reference = "SU-02";
        attribute :>> px4 = "v1.16.2";
        attribute :>> outcome = "landed-at-stale-home";
        attribute :>> keepoutMetres = 3.0;
        attribute :>> keepoutAltMetres = 8.0;
        attribute :>> minPilotDistanceLowMetres = 21.89;
        attribute :>> walkerMoved = true;
    }
}
