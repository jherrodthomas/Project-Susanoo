// LookLibrary — generated by tools/figures/lookslib_readme.py from sim/scenes3d/library.
// Do not edit by hand: change the library or the generator and regenerate.
// Status: picture only; no look changes a run.

package LookLibrary {
    private import ScalarValues::*;
    doc /* The look-only library of the 3D scenes (sim/scenes3d/library/README.md). */
    part def Environment {
        doc /* Picture only: ground, sky and grid colours and the extent drawn. */
        attribute ground : String;
        attribute ground2 : String;
        attribute sky : String;
        attribute grid : String;
        attribute extentMetres : Real;
    }
    part def Condition {
        doc /* Picture only: lighting and fog. Never changes a run. */
        attribute sun : Real;
        attribute ambient : Real;
        attribute fogMetres : Real [0..1];
        attribute skyTint : String [0..1];
    }
    part def Look {
        attribute camera : String;
        part environment : Environment;
        part condition : Condition;
    }
    part hillsideEnvironment : Environment {
        attribute :>> ground = "#7d8c5a";
        attribute :>> ground2 = "#6f7e4f";
        attribute :>> sky = "#cfe2f3";
        attribute :>> grid = "#5f6d44";
        attribute :>> extentMetres = 40.0;
    }
    part yardEnvironment : Environment {
        attribute :>> ground = "#9aa1a8";
        attribute :>> ground2 = "#8b9299";
        attribute :>> sky = "#dfe8f1";
        attribute :>> grid = "#7b838b";
        attribute :>> extentMetres = 30.0;
    }
    part fieldEnvironment : Environment {
        attribute :>> ground = "#8a9b62";
        attribute :>> ground2 = "#7a8b55";
        attribute :>> sky = "#cde0f2";
        attribute :>> grid = "#6a7a48";
        attribute :>> extentMetres = 160.0;
    }
    part clearCondition : Condition {
        attribute :>> sun = 1.0;
        attribute :>> ambient = 0.65;
    }
    part overcastCondition : Condition {
        attribute :>> sun = 0.45;
        attribute :>> ambient = 0.8;
        attribute :>> skyTint = "#c4ccd4";
    }
    part duskCondition : Condition {
        attribute :>> sun = 0.35;
        attribute :>> ambient = 0.45;
        attribute :>> skyTint = "#4a5578";
    }
    part fogCondition : Condition {
        attribute :>> sun = 0.4;
        attribute :>> ambient = 0.85;
        attribute :>> fogMetres = 70.0;
        attribute :>> skyTint = "#d7dde2";
    }
}
