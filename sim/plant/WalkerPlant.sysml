// WalkerPlant — generated by tools/figures/plant_readme.py from sim/spec/walker.yaml.
// Do not edit by hand: change the spec or the generator and regenerate.
// Status: reduced-order plant assumptions; synthetic, no evidence credit.

package WalkerPlant {
    private import ScalarValues::*;
    doc /* The level-1 walker plant (sim/plant/README.md). */
    part def WalkerPlant {
        doc /* SPEC-WLK-001 revision 0.1-draft: reduced-order plant parameters; every value an assumption, not a design value. */
        attribute massKg : Real = 4590.0;  // kg, derived
        attribute comHeightM : Real = 2.72;  // m, derived
        attribute crouchHeightM : Real = 1.49;  // m, derived
        attribute footHalfLengthM : Real = 0.6;  // m, assumed
        attribute stanceHalfLengthM : Real = 1.4;  // m, assumed
        attribute tipOffsetM : Real = 1.0;  // m, assumed
        attribute legForceRatio : Real = 2.0;  // -, assumed
        attribute stepTimeS : Real = 0.5;  // s, assumed
        attribute crouchRateMps : Real = 0.3;  // m/s, assumed
        attribute safeDropSpeedMps : Real = 1.0;  // m/s, assumed
        attribute slopeLean : Real = 0.25;  // -, assumed
        attribute swayAmplitudeM : Real = 0.1;  // m, assumed
        attribute swayPeriodS : Real = 1.2;  // s, assumed
        attribute balanceGain : Real = 1.5;  // -, assumed
        attribute heightKp : Real = 25.0;  // 1/s2, assumed
        attribute heightKd : Real = 10.0;  // 1/s, assumed
        attribute lowSupplyAlarm : Real = 0.7;  // -, assumed
        attribute lockThreshold : Real = 0.4;  // -, assumed
        attribute lockDelayS : Real = 0.1;  // s, assumed
        attribute monitorDetectS : Real = 0.15;  // s, assumed
        attribute electricSagFloor : Real = 0.35;  // -, assumed
        attribute dtS : Real = 0.005;  // s, assumed
        attribute horizonS : Real = 6.0;  // s, assumed
        attribute gravityMps2 : Real = 9.81;  // m/s2, published
    }
    part def FaultCase {
        doc /* One run of the fault catalogue: a fault, a configuration of the mitigations and a slope. */
        attribute actuationVariant : String;
        attribute fault : String;
        attribute slopeDeg : Real;
        attribute loadHolding : String;
        attribute monitor : Boolean;
        attribute pilotReactionS : Real;
        ref part plant : WalkerPlant;
    }
}
