// HazardScenes — generated by tools/figures/simfigs_readme.py from sim/figures/scenes.py and the committed SITL results.
// Do not edit by hand: change the scenes or the generator and regenerate.
// Status: pictures of synthetic simulation output; no evidence credit.

package HazardScenes {
    private import ScalarValues::*;
    doc /* The 2D hazard scenes (sim/figures/README.md). */
    part def HazardScene {
        doc /* An animated 2D scene of a synthetic run that shows a hazard. */
        attribute hazards : String;
        attribute replays : String;
        attribute performedOutcome : String;
    }
    part def SideViewScene :> HazardScene {
        doc /* Walker side view: the intended run dashed green, the performed run solid red; freezes at the first mishap. */
        attribute intendedOutcome : String;
    }
    part def TopDownScene :> HazardScene {
        doc /* UAV top-down view: overview of fence, walker and path, with a zoom on the dock. */
        attribute contract : String;
    }
    part sc01 : SideViewScene {
        doc /* SC-01: Slow supply leak on a slope: balance lost before the hold engages */
        attribute :>> hazards = "HAZ-WLK-002";
        attribute :>> replays = "edge case EC-08 (search SF-01)";
        attribute :>> performedOutcome = "tip";
        attribute :>> intendedOutcome = "safe";
    }
    part sc02 : SideViewScene {
        doc /* SC-02: Protective stop removes leg force instead of crouching */
        attribute :>> hazards = "HAZ-SAF-001";
        attribute :>> replays = "fault FLT-03";
        attribute :>> performedOutcome = "hard-drop";
        attribute :>> intendedOutcome = "safe";
    }
    part sc03 : SideViewScene {
        doc /* SC-03: Frozen posture feedback with no staleness monitor */
        attribute :>> hazards = "HAZ-WLK-001";
        attribute :>> replays = "fault FLT-02";
        attribute :>> performedOutcome = "tip";
        attribute :>> intendedOutcome = "safe";
    }
    part sc04 : SideViewScene {
        doc /* SC-04: Burst supply loss with failed load holding: cockpit drops */
        attribute :>> hazards = "HAZ-PIL-002";
        attribute :>> replays = "edge case EC-01 (search SF-01)";
        attribute :>> performedOutcome = "hard-drop";
        attribute :>> intendedOutcome = "safe";
    }
    part su01 : TopDownScene {
        doc /* SU-01: GCS link lost during observation, return-to-launch configured */
        attribute :>> hazards = "HAZ-INT-001";
        attribute :>> replays = "PX4 SITL run SU-01";
        attribute :>> performedOutcome = "keepout-breach";
        attribute :>> contract = "Loss of the integration link must invoke a defined, analysed";
    }
    part su02 : TopDownScene {
        doc /* SU-02: GCS link lost, return-to-launch, walker has moved since take-off */
        attribute :>> hazards = "HAZ-INT-001, HAZ-DCK-002";
        attribute :>> replays = "PX4 SITL run SU-02";
        attribute :>> performedOutcome = "landed-at-stale-home";
        attribute :>> contract = "PX4 home is the take-off point; the dock has moved with the ";
    }
    part su03 : TopDownScene {
        doc /* SU-03: GCS link lost during observation, land in place configured */
        attribute :>> hazards = "HAZ-INT-001";
        attribute :>> replays = "PX4 SITL run SU-03";
        attribute :>> performedOutcome = "landed-clear";
        attribute :>> contract = "Alternative contingency: land away from the walker";
    }
    part su04 : TopDownScene {
        doc /* SU-04: Battery failure during observation */
        attribute :>> hazards = "HAZ-INT-001";
        attribute :>> replays = "PX4 SITL run SU-04";
        attribute :>> performedOutcome = "landed-clear";
        attribute :>> contract = "Battery contingency must not bring the aircraft into the pil";
    }
    part su05 : TopDownScene {
        doc /* SU-05: Commanded beyond the geofence */
        attribute :>> hazards = "HAZ-INT-001";
        attribute :>> replays = "PX4 SITL run SU-05";
        attribute :>> performedOutcome = "contained";
        attribute :>> contract = "Operations stay inside the defined volume (EXT-AIRSPACE)";
    }
    part su06 : TopDownScene {
        doc /* SU-06: GPS lost during observation (emulated) */
        attribute :>> hazards = "HAZ-INT-001";
        attribute :>> replays = "PX4 SITL run SU-06";
        attribute :>> performedOutcome = "landed-clear";
        attribute :>> contract = "Navigation loss contingency; drift towards people or the wal";
    }
}
