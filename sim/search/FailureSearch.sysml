// FailureSearch — generated by tools/figures/search_readme.py from the docstring of sim/search/search.py.
// Do not edit by hand: change the search or the generator and regenerate.
// Status: method of a synthetic design aid; no evidence credit.

package FailureSearch {
    doc /* The failure search over the level-1 walker plant (sim/search/README.md). */
    action def SearchFamily {
        doc /* The failure search for one family, as the numbered steps of sim/search/search.py. */
        action monteCarlo { doc /* Monte Carlo */ }
        action crossEntropyFalsification { doc /* Cross-entropy falsification */ }
        action edgeCases { doc /* Edge cases */ }
        action mapToHazards { doc /* Map edge cases to hazards; unmapped outcomes become findings */ }
        first start then monteCarlo;
        first monteCarlo then crossEntropyFalsification;
        first crossEntropyFalsification then edgeCases;
        first edgeCases then mapToHazards;
        first mapToHazards then done;
        // iteration: crossEntropyFalsification -> crossEntropyFalsification when 6 rounds (informal; merge node omitted)
    }
}
