// SimulationEvidence — generated by tools/figures/sim_readme.py from the evidence gate in sim/README.md.
// Do not edit by hand: change the generator and regenerate.
// Status: when a simulation result may count as evidence; not evidence itself.

package SimulationEvidence {
    doc /* Evidence gate for simulation results (sim/README.md; rule R13 for the fidelity case). */
    attribute def FidelityCaseApproved;
    attribute def ModelOrParameterChanged;
    attribute def SafetyLeadTakesItIn;
    state def EvidenceGate {
        doc /* When a simulation result may count as evidence: the evidence gate of sim/README.md. */
        entry; then Synthetic;
        state Synthetic { doc /* data_kind synthetic, no evidence credit */ }
        state FidelityApproved { doc /* fidelity case for its family approved by a review record (R13) */ }
        state InAnalysis { doc /* taken into the owning analysis by the safety lead */ }
        transition t1 first Synthetic accept FidelityCaseApproved then FidelityApproved;
        transition t2 first FidelityApproved accept SafetyLeadTakesItIn then InAnalysis;
        transition t3 first FidelityApproved accept ModelOrParameterChanged then Synthetic;
        transition t4 first InAnalysis accept ModelOrParameterChanged then Synthetic;
    }
}
