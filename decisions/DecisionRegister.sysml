// DecisionRegister — generated by tools/figures/decisions_readme.py from decisions/register.yaml and rule D01.
// Do not edit by hand: change the generator or the register and regenerate.
// Status: lifecycle of a decision entry; not a decision itself.

package DecisionRegister {
    doc /* Lifecycle of one decision in decisions/register.yaml (schema statuses, rule D01). */
    attribute def BatchOpened;
    attribute def ChangeApplied;
    attribute def ClaudeDecidesReversibleChoice;
    attribute def LeadAnswers;
    attribute def Superseded;
    state def DecisionLifecycle {
        doc /* Lifecycle of one entry in decisions/register.yaml, as the schema statuses and rule D01 enforce it. */
        entry; then Queued;
        state Queued { doc /* written and waiting for a batch */ }
        state Open { doc /* asked; about ten at a time */ }
        state Answered { doc /* the lead's words recorded */ }
        state Applied { doc /* applied_in names every changed file */ }
        state Withdrawn { doc /* no longer needed */ }
        transition t1 first Queued accept BatchOpened then Open;
        transition t2 first Open accept LeadAnswers then Answered;
        transition t3 first Answered accept ChangeApplied then Applied;
        transition t4 first Queued accept ClaudeDecidesReversibleChoice then Applied;
        transition t5 first Open accept Superseded then Withdrawn;
        transition t6 first Queued accept Superseded then Withdrawn;
    }
}
