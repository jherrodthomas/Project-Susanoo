// ConceptLayouts — generated by tools/figures/cad_readme.py from cad/metrics.json.
// Do not edit by hand: change the layout parameters, rebuild the CAD and regenerate.
// Status: placeholder concept geometry (SUS-CAD-001), not a design.

package ConceptLayouts {
    private import ScalarValues::*;
    doc /* Concept layouts of SUS-M1 with standing metrics of their placeholder geometry. */
    part def ConceptLayout {
        doc /* A concept layout of placeholder geometry (SUS-CAD-001); values are not design data. */
        attribute height : Real;  // m
        attribute cockpitFloor : Real;  // m
        attribute placeholderMass : Real;  // kg
        attribute staticMargin : Real;  // m
        attribute rotorToPilot : Real;  // m
    }
    part cl01 : ConceptLayout {
        doc /* CL-01 Biped, seated protected cockpit, rear backpack dock */
        attribute :>> height = 4.08;
        attribute :>> cockpitFloor = 2.33;
        attribute :>> placeholderMass = 5010.0;
        attribute :>> staticMargin = 0.142;
        attribute :>> rotorToPilot = 0.79;
    }
    part cl02 : ConceptLayout {
        doc /* CL-02 Biped, seated protected cockpit, shoulder-mounted dock */
        attribute :>> height = 4.2;
        attribute :>> cockpitFloor = 2.33;
        attribute :>> placeholderMass = 5000.0;
        attribute :>> staticMargin = 0.145;
        attribute :>> rotorToPilot = 0.63;
    }
    part cl03 : ConceptLayout {
        doc /* CL-03 Biped, seated protected cockpit, separate portable station */
        attribute :>> height = 3.85;
        attribute :>> cockpitFloor = 2.33;
        attribute :>> placeholderMass = 4970.0;
        attribute :>> staticMargin = 0.144;
        attribute :>> rotorToPilot = 3.14;
    }
    part cl04 : ConceptLayout {
        doc /* CL-04 Biped armoured pod, seated cockpit, rear dock */
        attribute :>> height = 3.94;
        attribute :>> cockpitFloor = 1.94;
        attribute :>> placeholderMass = 6270.0;
        attribute :>> staticMargin = 0.225;
        attribute :>> rotorToPilot = 0.92;
    }
    part cl05 : ConceptLayout {
        doc /* CL-05 Reverse-jointed pod biped, claw arms, rear dock (reference layout, DQ-014) */
        attribute :>> height = 4.48;
        attribute :>> cockpitFloor = 2.41;
        attribute :>> placeholderMass = 4590.0;
        attribute :>> staticMargin = 0.378;
        attribute :>> rotorToPilot = 1.09;
    }
}
