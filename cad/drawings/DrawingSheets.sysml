// DrawingSheets — generated by tools/figures/drawings_readme.py from cad/drawings.
// Do not edit by hand: rebuild the sheets (tools/cad/make.sh) or change the generator and regenerate.
// Status: concept layout sheets for review; not a design, not for manufacture.

package DrawingSheets {
    private import ScalarValues::*;
    doc /* The concept layout drawing sheets (cad/drawings/README.md). */
    part def TitleBlock {
        attribute revision : String;
        attribute status : String;
        attribute source : String;
    }
    part def View {
        doc /* Third-angle: side elevation, plan above it, front view to the right. */
        attribute direction : String;
    }
    part def PrintedMetrics {
        doc /* The numbers the sheet prints, read from cad/metrics.json. */
        attribute heightMm : Real;
        attribute cgHeightMm : Real;
        attribute staticMarginMm : Real;
        attribute tipAngleDeg : Real;
        attribute rotorToPilotMm : Real;
    }
    part def DrawingSheet {
        doc /* One A3 concept-layout sheet (tools/cad/drawings.py). */
        attribute drawingNumber : String;
        attribute layoutId : String;
        attribute posture : String;
        attribute scaleDenominator : Integer;
        part titleBlock : TitleBlock;
        part views : View [3];
        part printed : PrintedMetrics;
    }
    part sheetCL01 : DrawingSheet {
        attribute :>> drawingNumber = "SUS-CAD-001-CL-01";
        attribute :>> layoutId = "CL-01";
        attribute :>> posture = "standing";
        attribute :>> scaleDenominator = 50;
        part :>> titleBlock {
            attribute :>> revision = "0.21-draft";
            attribute :>> status = "CONCEPT, NOT REVIEWED";
            attribute :>> source = "cad/params/CL-01.yaml";
        }
        part :>> printed {
            attribute :>> heightMm = 4080.0;
            attribute :>> cgHeightMm = 2634.0;
            attribute :>> staticMarginMm = 142.0;
            attribute :>> tipAngleDeg = 3.1;
            attribute :>> rotorToPilotMm = 790.0;
        }
    }
    part sheetCL02 : DrawingSheet {
        attribute :>> drawingNumber = "SUS-CAD-001-CL-02";
        attribute :>> layoutId = "CL-02";
        attribute :>> posture = "standing";
        attribute :>> scaleDenominator = 50;
        part :>> titleBlock {
            attribute :>> revision = "0.21-draft";
            attribute :>> status = "CONCEPT, NOT REVIEWED";
            attribute :>> source = "cad/params/CL-02.yaml";
        }
        part :>> printed {
            attribute :>> heightMm = 4200.0;
            attribute :>> cgHeightMm = 2634.0;
            attribute :>> staticMarginMm = 145.0;
            attribute :>> tipAngleDeg = 3.2;
            attribute :>> rotorToPilotMm = 630.0;
        }
    }
    part sheetCL03 : DrawingSheet {
        attribute :>> drawingNumber = "SUS-CAD-001-CL-03";
        attribute :>> layoutId = "CL-03";
        attribute :>> posture = "standing";
        attribute :>> scaleDenominator = 50;
        part :>> titleBlock {
            attribute :>> revision = "0.21-draft";
            attribute :>> status = "CONCEPT, NOT REVIEWED";
            attribute :>> source = "cad/params/CL-03.yaml";
        }
        part :>> printed {
            attribute :>> heightMm = 3850.0;
            attribute :>> cgHeightMm = 2626.0;
            attribute :>> staticMarginMm = 144.0;
            attribute :>> tipAngleDeg = 3.1;
            attribute :>> rotorToPilotMm = 3140.0;
        }
    }
    part sheetCL04 : DrawingSheet {
        attribute :>> drawingNumber = "SUS-CAD-001-CL-04";
        attribute :>> layoutId = "CL-04";
        attribute :>> posture = "standing";
        attribute :>> scaleDenominator = 50;
        part :>> titleBlock {
            attribute :>> revision = "0.21-draft";
            attribute :>> status = "CONCEPT, NOT REVIEWED";
            attribute :>> source = "cad/params/CL-04.yaml";
        }
        part :>> printed {
            attribute :>> heightMm = 3940.0;
            attribute :>> cgHeightMm = 2236.0;
            attribute :>> staticMarginMm = 225.0;
            attribute :>> tipAngleDeg = 5.7;
            attribute :>> rotorToPilotMm = 920.0;
        }
    }
    part sheetCL05carry : DrawingSheet {
        attribute :>> drawingNumber = "SUS-CAD-001-CL-05-carry";
        attribute :>> layoutId = "CL-05";
        attribute :>> posture = "carry";
        attribute :>> scaleDenominator = 50;
        part :>> titleBlock {
            attribute :>> revision = "0.21-draft";
            attribute :>> status = "CONCEPT, NOT REVIEWED";
            attribute :>> source = "cad/params/CL-05.yaml";
        }
        part :>> printed {
            attribute :>> heightMm = 4480.0;
            attribute :>> cgHeightMm = 2715.0;
            attribute :>> staticMarginMm = 350.0;
            attribute :>> tipAngleDeg = 7.4;
            attribute :>> rotorToPilotMm = 1090.0;
        }
    }
    part sheetCL05emergency : DrawingSheet {
        attribute :>> drawingNumber = "SUS-CAD-001-CL-05-emergency";
        attribute :>> layoutId = "CL-05";
        attribute :>> posture = "emergency";
        attribute :>> scaleDenominator = 50;
        part :>> titleBlock {
            attribute :>> revision = "0.21-draft";
            attribute :>> status = "CONCEPT, NOT REVIEWED";
            attribute :>> source = "cad/params/CL-05.yaml";
        }
        part :>> printed {
            attribute :>> heightMm = 4480.0;
            attribute :>> cgHeightMm = 2725.0;
            attribute :>> staticMarginMm = 378.0;
            attribute :>> tipAngleDeg = 7.9;
            attribute :>> rotorToPilotMm = 1090.0;
        }
    }
    part sheetCL05kneel : DrawingSheet {
        attribute :>> drawingNumber = "SUS-CAD-001-CL-05-kneel";
        attribute :>> layoutId = "CL-05";
        attribute :>> posture = "kneel";
        attribute :>> scaleDenominator = 50;
        part :>> titleBlock {
            attribute :>> revision = "0.21-draft";
            attribute :>> status = "CONCEPT, NOT REVIEWED";
            attribute :>> source = "cad/params/CL-05.yaml";
        }
        part :>> printed {
            attribute :>> heightMm = 3100.0;
            attribute :>> cgHeightMm = 1493.0;
            attribute :>> staticMarginMm = 349.0;
            attribute :>> tipAngleDeg = 13.1;
            attribute :>> rotorToPilotMm = 1090.0;
        }
    }
    part sheetCL05 : DrawingSheet {
        attribute :>> drawingNumber = "SUS-CAD-001-CL-05";
        attribute :>> layoutId = "CL-05";
        attribute :>> posture = "standing";
        attribute :>> scaleDenominator = 50;
        part :>> titleBlock {
            attribute :>> revision = "0.21-draft";
            attribute :>> status = "CONCEPT, NOT REVIEWED";
            attribute :>> source = "cad/params/CL-05.yaml";
        }
        part :>> printed {
            attribute :>> heightMm = 4480.0;
            attribute :>> cgHeightMm = 2723.0;
            attribute :>> staticMarginMm = 378.0;
            attribute :>> tipAngleDeg = 7.9;
            attribute :>> rotorToPilotMm = 1090.0;
        }
    }
}
