// LayoutParameters — generated by tools/figures/params_readme.py from cad/params.
// Do not edit by hand: change the parameter files or the generator and regenerate.
// Status: placeholder concept parameters for review and alignment; not design data.

package LayoutParameters {
    private import ScalarValues::*;
    doc /* The concept layout parameters (cad/params/README.md). */
    part def Leg {
        attribute hipHalfWidth : Real;
        attribute thigh : Real;
        attribute shank : Real;
        attribute kneeForward : Real;
        attribute ankleHeight : Real;
    }
    part def Arm {
        attribute upper : Real;
        attribute fore : Real;
        attribute radius : Real;
    }
    part def Dock {
        attribute dockType : String;
    }
    part def CommonParameters {
        doc /* Shared by every layout (common.yaml): scale figure, the docked UAV and placeholder densities. */
        attribute referenceHumanHeight : Real;
        attribute uavRotorRadius : Real;
        attribute uavArmReach : Real;
    }
    part def Layout {
        doc /* One concept layout (CL-nn.yaml). Placeholder values in metres. */
        attribute layoutId : String;
        attribute title : String;
        attribute locomotion : String;
        attribute style : String;
        part leg : Leg;
        part arm : Arm;
        part dock : Dock;
    }
    part common : CommonParameters {
        attribute :>> referenceHumanHeight = 1.75;
        attribute :>> uavRotorRadius = 0.16;
        attribute :>> uavArmReach = 0.3;
    }
    part layoutCL01 : Layout {
        attribute :>> layoutId = "CL-01";
        attribute :>> title = "Biped, seated protected cockpit, rear backpack dock";
        attribute :>> locomotion = "biped";
        attribute :>> style = "open-frame";
        part :>> leg {
            attribute :>> hipHalfWidth = 0.62;
            attribute :>> thigh = 1.1;
            attribute :>> shank = 1.1;
            attribute :>> kneeForward = 0.2;
            attribute :>> ankleHeight = 0.32;
        }
        part :>> arm {
            attribute :>> upper = 1.0;
            attribute :>> fore = 0.95;
            attribute :>> radius = 0.1;
        }
        part :>> dock {
            attribute :>> dockType = "rear-backpack";
        }
    }
    part layoutCL02 : Layout {
        attribute :>> layoutId = "CL-02";
        attribute :>> title = "Biped, seated protected cockpit, shoulder-mounted dock";
        attribute :>> locomotion = "biped";
        attribute :>> style = "open-frame";
        part :>> leg {
            attribute :>> hipHalfWidth = 0.62;
            attribute :>> thigh = 1.1;
            attribute :>> shank = 1.1;
            attribute :>> kneeForward = 0.2;
            attribute :>> ankleHeight = 0.32;
        }
        part :>> arm {
            attribute :>> upper = 1.0;
            attribute :>> fore = 0.95;
            attribute :>> radius = 0.1;
        }
        part :>> dock {
            attribute :>> dockType = "shoulder";
        }
    }
    part layoutCL03 : Layout {
        attribute :>> layoutId = "CL-03";
        attribute :>> title = "Biped, seated protected cockpit, separate portable station";
        attribute :>> locomotion = "biped";
        attribute :>> style = "open-frame";
        part :>> leg {
            attribute :>> hipHalfWidth = 0.62;
            attribute :>> thigh = 1.1;
            attribute :>> shank = 1.1;
            attribute :>> kneeForward = 0.2;
            attribute :>> ankleHeight = 0.32;
        }
        part :>> arm {
            attribute :>> upper = 1.0;
            attribute :>> fore = 0.95;
            attribute :>> radius = 0.1;
        }
        part :>> dock {
            attribute :>> dockType = "ground-station";
        }
    }
    part layoutCL04 : Layout {
        attribute :>> layoutId = "CL-04";
        attribute :>> title = "Biped armoured pod, seated cockpit, rear dock";
        attribute :>> locomotion = "biped";
        attribute :>> style = "armored-pod";
        part :>> leg {
            attribute :>> hipHalfWidth = 0.58;
            attribute :>> thigh = 0.9;
            attribute :>> shank = 0.88;
            attribute :>> kneeForward = 0.3;
            attribute :>> ankleHeight = 0.34;
        }
        part :>> arm {
            attribute :>> upper = 0.8;
            attribute :>> fore = 0.78;
            attribute :>> radius = 0.12;
        }
        part :>> dock {
            attribute :>> dockType = "rear-backpack";
        }
    }
    part layoutCL05 : Layout {
        attribute :>> layoutId = "CL-05";
        attribute :>> title = "Reverse-jointed pod biped, claw arms, rear dock";
        attribute :>> locomotion = "biped";
        attribute :>> style = "build123d";
        part :>> leg {
            attribute :>> hipHalfWidth = 0.55;
            attribute :>> thigh = 1.0;
            attribute :>> shank = 1.05;
            attribute :>> kneeForward = -0.45;
            attribute :>> ankleHeight = 0.55;
        }
        part :>> arm {
            attribute :>> upper = 0.95;
            attribute :>> fore = 0.85;
            attribute :>> radius = 0.1;
        }
        part :>> dock {
            attribute :>> dockType = "rear-backpack";
        }
    }
}
