// BlenderRenders — generated by tools/figures/blender_readme.py from cad/renders/blender.
// Do not edit by hand: re-render (blender_render.py, blender_walk.py) or change the generator and regenerate.
// Status: renders of placeholder concept geometry, for communication; not a design.

package BlenderRenders {
    private import ScalarValues::*;
    doc /* The Blender stills and walk clips of CL-05 (cad/renders/blender/README.md). */
    part def Shot {
        doc /* A camera on the walker: offset from the footprint centre, look height, lens. */
        attribute sourceLayout : String;
        attribute cameraOffsetM : Real [3];
        attribute lookFraction : Real;
        attribute lensMm : Real;
    }
    part def BlenderStill {
        attribute fileName : String;
        attribute livery : String;
        attribute widthPx : Integer;
        attribute heightPx : Integer;
        part shot : Shot;
    }
    part def WalkClip {
        attribute fileName : String;
        attribute livery : String;
        attribute loaded : Boolean;
        attribute seconds : Real;
    }
    part stillCl05Hero : BlenderStill {
        attribute :>> fileName = "CL-05-hero.jpg";
        attribute :>> livery = "industrial";
        attribute :>> widthPx = 1600;
        attribute :>> heightPx = 1000;
        part :>> shot {
            attribute :>> sourceLayout = "CL-05";
            attribute :>> cameraOffsetM = (7.2, -5.0, 1.7);
            attribute :>> lookFraction = 0.48;
            attribute :>> lensMm = 35.0;
        }
    }
    part stillCl05HeroMilitary : BlenderStill {
        attribute :>> fileName = "CL-05-hero-military.jpg";
        attribute :>> livery = "military";
        attribute :>> widthPx = 1600;
        attribute :>> heightPx = 1000;
        part :>> shot {
            attribute :>> sourceLayout = "CL-05";
            attribute :>> cameraOffsetM = (7.2, -5.0, 1.7);
            attribute :>> lookFraction = 0.48;
            attribute :>> lensMm = 35.0;
        }
    }
    part stillCl05Rear : BlenderStill {
        attribute :>> fileName = "CL-05-rear.jpg";
        attribute :>> livery = "industrial";
        attribute :>> widthPx = 1600;
        attribute :>> heightPx = 1000;
        part :>> shot {
            attribute :>> sourceLayout = "CL-05";
            attribute :>> cameraOffsetM = (-7.0, -7.5, 2.8);
            attribute :>> lookFraction = 0.45;
            attribute :>> lensMm = 35.0;
        }
    }
    part stillCl05RearMilitary : BlenderStill {
        attribute :>> fileName = "CL-05-rear-military.jpg";
        attribute :>> livery = "military";
        attribute :>> widthPx = 1600;
        attribute :>> heightPx = 1000;
        part :>> shot {
            attribute :>> sourceLayout = "CL-05";
            attribute :>> cameraOffsetM = (-7.0, -7.5, 2.8);
            attribute :>> lookFraction = 0.45;
            attribute :>> lensMm = 35.0;
        }
    }
    part stillCl05Kneel : BlenderStill {
        attribute :>> fileName = "CL-05-kneel.jpg";
        attribute :>> livery = "industrial";
        attribute :>> widthPx = 1600;
        attribute :>> heightPx = 1000;
        part :>> shot {
            attribute :>> sourceLayout = "CL-05-kneel";
            attribute :>> cameraOffsetM = (6.4, -4.2, 1.6);
            attribute :>> lookFraction = 0.45;
            attribute :>> lensMm = 35.0;
        }
    }
    part stillCl05KneelMilitary : BlenderStill {
        attribute :>> fileName = "CL-05-kneel-military.jpg";
        attribute :>> livery = "military";
        attribute :>> widthPx = 1600;
        attribute :>> heightPx = 1000;
        part :>> shot {
            attribute :>> sourceLayout = "CL-05-kneel";
            attribute :>> cameraOffsetM = (6.4, -4.2, 1.6);
            attribute :>> lookFraction = 0.45;
            attribute :>> lensMm = 35.0;
        }
    }
    part stillCl05Emergency : BlenderStill {
        attribute :>> fileName = "CL-05-emergency.jpg";
        attribute :>> livery = "industrial";
        attribute :>> widthPx = 1600;
        attribute :>> heightPx = 1000;
        part :>> shot {
            attribute :>> sourceLayout = "CL-05-emergency";
            attribute :>> cameraOffsetM = (2.2, -8.0, 2.4);
            attribute :>> lookFraction = 0.5;
            attribute :>> lensMm = 35.0;
        }
    }
    part stillCl05EmergencyMilitary : BlenderStill {
        attribute :>> fileName = "CL-05-emergency-military.jpg";
        attribute :>> livery = "military";
        attribute :>> widthPx = 1600;
        attribute :>> heightPx = 1000;
        part :>> shot {
            attribute :>> sourceLayout = "CL-05-emergency";
            attribute :>> cameraOffsetM = (2.2, -8.0, 2.4);
            attribute :>> lookFraction = 0.5;
            attribute :>> lensMm = 35.0;
        }
    }
    part stillCl05Carry : BlenderStill {
        attribute :>> fileName = "CL-05-carry.jpg";
        attribute :>> livery = "industrial";
        attribute :>> widthPx = 1600;
        attribute :>> heightPx = 1000;
        part :>> shot {
            attribute :>> sourceLayout = "CL-05-carry";
            attribute :>> cameraOffsetM = (7.6, -4.6, 1.7);
            attribute :>> lookFraction = 0.45;
            attribute :>> lensMm = 35.0;
        }
    }
    part stillCl05CarryMilitary : BlenderStill {
        attribute :>> fileName = "CL-05-carry-military.jpg";
        attribute :>> livery = "military";
        attribute :>> widthPx = 1600;
        attribute :>> heightPx = 1000;
        part :>> shot {
            attribute :>> sourceLayout = "CL-05-carry";
            attribute :>> cameraOffsetM = (7.6, -4.6, 1.7);
            attribute :>> lookFraction = 0.45;
            attribute :>> lensMm = 35.0;
        }
    }
    part clipCl05WalkLoadedMilitaryGif : WalkClip {
        attribute :>> fileName = "CL-05-walk-loaded-military.gif";
        attribute :>> livery = "military";
        attribute :>> loaded = true;
        attribute :>> seconds = 3.0;
    }
    part clipCl05WalkLoadedMilitaryMp4 : WalkClip {
        attribute :>> fileName = "CL-05-walk-loaded-military.mp4";
        attribute :>> livery = "military";
        attribute :>> loaded = true;
        attribute :>> seconds = 9.0;
    }
    part clipCl05WalkMilitaryGif : WalkClip {
        attribute :>> fileName = "CL-05-walk-military.gif";
        attribute :>> livery = "military";
        attribute :>> loaded = false;
        attribute :>> seconds = 3.0;
    }
    part clipCl05WalkMilitaryMp4 : WalkClip {
        attribute :>> fileName = "CL-05-walk-military.mp4";
        attribute :>> livery = "military";
        attribute :>> loaded = false;
        attribute :>> seconds = 9.0;
    }
}
