// ReviewRenders — generated by tools/figures/renders_readme.py from cad/renders.
// Do not edit by hand: re-render (tools/cad/make.sh) or change the generator and regenerate.
// Status: renders of placeholder concept geometry, for review and communication; not a design.

package ReviewRenders {
    private import ScalarValues::*;
    doc /* The concept layout renders (cad/renders/README.md). */
    part def Render {
        doc /* One image or clip in cad/renders, rendered from the CAD meshes. */
        attribute fileName : String;
        attribute producer : String;
        attribute shownByPages : Integer;
    }
    part def ReviewRender :> Render {
        attribute layoutId : String;
        attribute viewName : String;
        attribute widthPx : Integer;
        attribute heightPx : Integer;
    }
    part def BlenderRender :> Render {
        attribute shot : String;
        attribute livery : String;
        attribute sourceLayout : String;
    }
    part def WalkClip :> Render {
        attribute format : String;
    }
    part reviewCl01Hero : ReviewRender {
        attribute :>> fileName = "CL-01-hero.png";
        attribute :>> producer = "tools/cad/render.cjs";
        attribute :>> shownByPages = 2;
        attribute :>> layoutId = "CL-01";
        attribute :>> viewName = "hero";
        attribute :>> widthPx = 2250;
        attribute :>> heightPx = 1440;
    }
    part reviewCl01Iso : ReviewRender {
        attribute :>> fileName = "CL-01-iso.png";
        attribute :>> producer = "tools/cad/render.cjs";
        attribute :>> shownByPages = 2;
        attribute :>> layoutId = "CL-01";
        attribute :>> viewName = "iso";
        attribute :>> widthPx = 2250;
        attribute :>> heightPx = 1440;
    }
    part reviewCl01Side : ReviewRender {
        attribute :>> fileName = "CL-01-side.png";
        attribute :>> producer = "tools/cad/render.cjs";
        attribute :>> shownByPages = 2;
        attribute :>> layoutId = "CL-01";
        attribute :>> viewName = "side";
        attribute :>> widthPx = 2250;
        attribute :>> heightPx = 1440;
    }
    part reviewCl01Top : ReviewRender {
        attribute :>> fileName = "CL-01-top.png";
        attribute :>> producer = "tools/cad/render.cjs";
        attribute :>> shownByPages = 2;
        attribute :>> layoutId = "CL-01";
        attribute :>> viewName = "top";
        attribute :>> widthPx = 2250;
        attribute :>> heightPx = 1440;
    }
    part reviewCl01Dock : ReviewRender {
        attribute :>> fileName = "CL-01-dock.png";
        attribute :>> producer = "tools/cad/render.cjs";
        attribute :>> shownByPages = 2;
        attribute :>> layoutId = "CL-01";
        attribute :>> viewName = "dock";
        attribute :>> widthPx = 2250;
        attribute :>> heightPx = 1440;
    }
    part reviewCl02Hero : ReviewRender {
        attribute :>> fileName = "CL-02-hero.png";
        attribute :>> producer = "tools/cad/render.cjs";
        attribute :>> shownByPages = 2;
        attribute :>> layoutId = "CL-02";
        attribute :>> viewName = "hero";
        attribute :>> widthPx = 2250;
        attribute :>> heightPx = 1440;
    }
    part reviewCl02Iso : ReviewRender {
        attribute :>> fileName = "CL-02-iso.png";
        attribute :>> producer = "tools/cad/render.cjs";
        attribute :>> shownByPages = 2;
        attribute :>> layoutId = "CL-02";
        attribute :>> viewName = "iso";
        attribute :>> widthPx = 2250;
        attribute :>> heightPx = 1440;
    }
    part reviewCl02Side : ReviewRender {
        attribute :>> fileName = "CL-02-side.png";
        attribute :>> producer = "tools/cad/render.cjs";
        attribute :>> shownByPages = 2;
        attribute :>> layoutId = "CL-02";
        attribute :>> viewName = "side";
        attribute :>> widthPx = 2250;
        attribute :>> heightPx = 1440;
    }
    part reviewCl02Top : ReviewRender {
        attribute :>> fileName = "CL-02-top.png";
        attribute :>> producer = "tools/cad/render.cjs";
        attribute :>> shownByPages = 2;
        attribute :>> layoutId = "CL-02";
        attribute :>> viewName = "top";
        attribute :>> widthPx = 2250;
        attribute :>> heightPx = 1440;
    }
    part reviewCl02Dock : ReviewRender {
        attribute :>> fileName = "CL-02-dock.png";
        attribute :>> producer = "tools/cad/render.cjs";
        attribute :>> shownByPages = 2;
        attribute :>> layoutId = "CL-02";
        attribute :>> viewName = "dock";
        attribute :>> widthPx = 2250;
        attribute :>> heightPx = 1440;
    }
    part reviewCl03Hero : ReviewRender {
        attribute :>> fileName = "CL-03-hero.png";
        attribute :>> producer = "tools/cad/render.cjs";
        attribute :>> shownByPages = 2;
        attribute :>> layoutId = "CL-03";
        attribute :>> viewName = "hero";
        attribute :>> widthPx = 2250;
        attribute :>> heightPx = 1440;
    }
    part reviewCl03Iso : ReviewRender {
        attribute :>> fileName = "CL-03-iso.png";
        attribute :>> producer = "tools/cad/render.cjs";
        attribute :>> shownByPages = 2;
        attribute :>> layoutId = "CL-03";
        attribute :>> viewName = "iso";
        attribute :>> widthPx = 2250;
        attribute :>> heightPx = 1440;
    }
    part reviewCl03Side : ReviewRender {
        attribute :>> fileName = "CL-03-side.png";
        attribute :>> producer = "tools/cad/render.cjs";
        attribute :>> shownByPages = 2;
        attribute :>> layoutId = "CL-03";
        attribute :>> viewName = "side";
        attribute :>> widthPx = 2250;
        attribute :>> heightPx = 1440;
    }
    part reviewCl03Top : ReviewRender {
        attribute :>> fileName = "CL-03-top.png";
        attribute :>> producer = "tools/cad/render.cjs";
        attribute :>> shownByPages = 2;
        attribute :>> layoutId = "CL-03";
        attribute :>> viewName = "top";
        attribute :>> widthPx = 2250;
        attribute :>> heightPx = 1440;
    }
    part reviewCl03Dock : ReviewRender {
        attribute :>> fileName = "CL-03-dock.png";
        attribute :>> producer = "tools/cad/render.cjs";
        attribute :>> shownByPages = 2;
        attribute :>> layoutId = "CL-03";
        attribute :>> viewName = "dock";
        attribute :>> widthPx = 2250;
        attribute :>> heightPx = 1440;
    }
    part reviewCl04Hero : ReviewRender {
        attribute :>> fileName = "CL-04-hero.png";
        attribute :>> producer = "tools/cad/render.cjs";
        attribute :>> shownByPages = 2;
        attribute :>> layoutId = "CL-04";
        attribute :>> viewName = "hero";
        attribute :>> widthPx = 2250;
        attribute :>> heightPx = 1440;
    }
    part reviewCl04Iso : ReviewRender {
        attribute :>> fileName = "CL-04-iso.png";
        attribute :>> producer = "tools/cad/render.cjs";
        attribute :>> shownByPages = 2;
        attribute :>> layoutId = "CL-04";
        attribute :>> viewName = "iso";
        attribute :>> widthPx = 2250;
        attribute :>> heightPx = 1440;
    }
    part reviewCl04Side : ReviewRender {
        attribute :>> fileName = "CL-04-side.png";
        attribute :>> producer = "tools/cad/render.cjs";
        attribute :>> shownByPages = 2;
        attribute :>> layoutId = "CL-04";
        attribute :>> viewName = "side";
        attribute :>> widthPx = 2250;
        attribute :>> heightPx = 1440;
    }
    part reviewCl04Top : ReviewRender {
        attribute :>> fileName = "CL-04-top.png";
        attribute :>> producer = "tools/cad/render.cjs";
        attribute :>> shownByPages = 2;
        attribute :>> layoutId = "CL-04";
        attribute :>> viewName = "top";
        attribute :>> widthPx = 2250;
        attribute :>> heightPx = 1440;
    }
    part reviewCl04Dock : ReviewRender {
        attribute :>> fileName = "CL-04-dock.png";
        attribute :>> producer = "tools/cad/render.cjs";
        attribute :>> shownByPages = 2;
        attribute :>> layoutId = "CL-04";
        attribute :>> viewName = "dock";
        attribute :>> widthPx = 2250;
        attribute :>> heightPx = 1440;
    }
    part reviewCl05Hero : ReviewRender {
        attribute :>> fileName = "CL-05-hero.png";
        attribute :>> producer = "tools/cad/render.cjs";
        attribute :>> shownByPages = 2;
        attribute :>> layoutId = "CL-05";
        attribute :>> viewName = "hero";
        attribute :>> widthPx = 2250;
        attribute :>> heightPx = 1440;
    }
    part reviewCl05Iso : ReviewRender {
        attribute :>> fileName = "CL-05-iso.png";
        attribute :>> producer = "tools/cad/render.cjs";
        attribute :>> shownByPages = 2;
        attribute :>> layoutId = "CL-05";
        attribute :>> viewName = "iso";
        attribute :>> widthPx = 2250;
        attribute :>> heightPx = 1440;
    }
    part reviewCl05Side : ReviewRender {
        attribute :>> fileName = "CL-05-side.png";
        attribute :>> producer = "tools/cad/render.cjs";
        attribute :>> shownByPages = 2;
        attribute :>> layoutId = "CL-05";
        attribute :>> viewName = "side";
        attribute :>> widthPx = 2250;
        attribute :>> heightPx = 1440;
    }
    part reviewCl05Top : ReviewRender {
        attribute :>> fileName = "CL-05-top.png";
        attribute :>> producer = "tools/cad/render.cjs";
        attribute :>> shownByPages = 2;
        attribute :>> layoutId = "CL-05";
        attribute :>> viewName = "top";
        attribute :>> widthPx = 2250;
        attribute :>> heightPx = 1440;
    }
    part reviewCl05Dock : ReviewRender {
        attribute :>> fileName = "CL-05-dock.png";
        attribute :>> producer = "tools/cad/render.cjs";
        attribute :>> shownByPages = 2;
        attribute :>> layoutId = "CL-05";
        attribute :>> viewName = "dock";
        attribute :>> widthPx = 2250;
        attribute :>> heightPx = 1440;
    }
    part reviewCl05KneelHero : ReviewRender {
        attribute :>> fileName = "CL-05-kneel-hero.png";
        attribute :>> producer = "tools/cad/render.cjs";
        attribute :>> shownByPages = 2;
        attribute :>> layoutId = "CL-05-kneel";
        attribute :>> viewName = "hero";
        attribute :>> widthPx = 2250;
        attribute :>> heightPx = 1440;
    }
    part reviewCl05KneelIso : ReviewRender {
        attribute :>> fileName = "CL-05-kneel-iso.png";
        attribute :>> producer = "tools/cad/render.cjs";
        attribute :>> shownByPages = 0;
        attribute :>> layoutId = "CL-05-kneel";
        attribute :>> viewName = "iso";
        attribute :>> widthPx = 2250;
        attribute :>> heightPx = 1440;
    }
    part reviewCl05KneelSide : ReviewRender {
        attribute :>> fileName = "CL-05-kneel-side.png";
        attribute :>> producer = "tools/cad/render.cjs";
        attribute :>> shownByPages = 2;
        attribute :>> layoutId = "CL-05-kneel";
        attribute :>> viewName = "side";
        attribute :>> widthPx = 2250;
        attribute :>> heightPx = 1440;
    }
    part reviewCl05KneelTop : ReviewRender {
        attribute :>> fileName = "CL-05-kneel-top.png";
        attribute :>> producer = "tools/cad/render.cjs";
        attribute :>> shownByPages = 0;
        attribute :>> layoutId = "CL-05-kneel";
        attribute :>> viewName = "top";
        attribute :>> widthPx = 2250;
        attribute :>> heightPx = 1440;
    }
    part reviewCl05KneelDock : ReviewRender {
        attribute :>> fileName = "CL-05-kneel-dock.png";
        attribute :>> producer = "tools/cad/render.cjs";
        attribute :>> shownByPages = 0;
        attribute :>> layoutId = "CL-05-kneel";
        attribute :>> viewName = "dock";
        attribute :>> widthPx = 2250;
        attribute :>> heightPx = 1440;
    }
    part reviewCl05CarryHero : ReviewRender {
        attribute :>> fileName = "CL-05-carry-hero.png";
        attribute :>> producer = "tools/cad/render.cjs";
        attribute :>> shownByPages = 2;
        attribute :>> layoutId = "CL-05-carry";
        attribute :>> viewName = "hero";
        attribute :>> widthPx = 2250;
        attribute :>> heightPx = 1440;
    }
    part reviewCl05CarryIso : ReviewRender {
        attribute :>> fileName = "CL-05-carry-iso.png";
        attribute :>> producer = "tools/cad/render.cjs";
        attribute :>> shownByPages = 0;
        attribute :>> layoutId = "CL-05-carry";
        attribute :>> viewName = "iso";
        attribute :>> widthPx = 2250;
        attribute :>> heightPx = 1440;
    }
    part reviewCl05CarrySide : ReviewRender {
        attribute :>> fileName = "CL-05-carry-side.png";
        attribute :>> producer = "tools/cad/render.cjs";
        attribute :>> shownByPages = 2;
        attribute :>> layoutId = "CL-05-carry";
        attribute :>> viewName = "side";
        attribute :>> widthPx = 2250;
        attribute :>> heightPx = 1440;
    }
    part reviewCl05CarryTop : ReviewRender {
        attribute :>> fileName = "CL-05-carry-top.png";
        attribute :>> producer = "tools/cad/render.cjs";
        attribute :>> shownByPages = 0;
        attribute :>> layoutId = "CL-05-carry";
        attribute :>> viewName = "top";
        attribute :>> widthPx = 2250;
        attribute :>> heightPx = 1440;
    }
    part reviewCl05CarryDock : ReviewRender {
        attribute :>> fileName = "CL-05-carry-dock.png";
        attribute :>> producer = "tools/cad/render.cjs";
        attribute :>> shownByPages = 0;
        attribute :>> layoutId = "CL-05-carry";
        attribute :>> viewName = "dock";
        attribute :>> widthPx = 2250;
        attribute :>> heightPx = 1440;
    }
    part reviewCl05EmergencyHero : ReviewRender {
        attribute :>> fileName = "CL-05-emergency-hero.png";
        attribute :>> producer = "tools/cad/render.cjs";
        attribute :>> shownByPages = 2;
        attribute :>> layoutId = "CL-05-emergency";
        attribute :>> viewName = "hero";
        attribute :>> widthPx = 2250;
        attribute :>> heightPx = 1440;
    }
    part reviewCl05EmergencyIso : ReviewRender {
        attribute :>> fileName = "CL-05-emergency-iso.png";
        attribute :>> producer = "tools/cad/render.cjs";
        attribute :>> shownByPages = 0;
        attribute :>> layoutId = "CL-05-emergency";
        attribute :>> viewName = "iso";
        attribute :>> widthPx = 2250;
        attribute :>> heightPx = 1440;
    }
    part reviewCl05EmergencySide : ReviewRender {
        attribute :>> fileName = "CL-05-emergency-side.png";
        attribute :>> producer = "tools/cad/render.cjs";
        attribute :>> shownByPages = 2;
        attribute :>> layoutId = "CL-05-emergency";
        attribute :>> viewName = "side";
        attribute :>> widthPx = 2250;
        attribute :>> heightPx = 1440;
    }
    part reviewCl05EmergencyTop : ReviewRender {
        attribute :>> fileName = "CL-05-emergency-top.png";
        attribute :>> producer = "tools/cad/render.cjs";
        attribute :>> shownByPages = 0;
        attribute :>> layoutId = "CL-05-emergency";
        attribute :>> viewName = "top";
        attribute :>> widthPx = 2250;
        attribute :>> heightPx = 1440;
    }
    part reviewCl05EmergencyDock : ReviewRender {
        attribute :>> fileName = "CL-05-emergency-dock.png";
        attribute :>> producer = "tools/cad/render.cjs";
        attribute :>> shownByPages = 0;
        attribute :>> layoutId = "CL-05-emergency";
        attribute :>> viewName = "dock";
        attribute :>> widthPx = 2250;
        attribute :>> heightPx = 1440;
    }
    part blenderCl05Hero : BlenderRender {
        attribute :>> fileName = "CL-05-hero.jpg";
        attribute :>> producer = "tools/cad/blender_render.py";
        attribute :>> shownByPages = 5;
        attribute :>> shot = "hero";
        attribute :>> livery = "industrial";
        attribute :>> sourceLayout = "CL-05";
    }
    part blenderCl05HeroMilitary : BlenderRender {
        attribute :>> fileName = "CL-05-hero-military.jpg";
        attribute :>> producer = "tools/cad/blender_render.py";
        attribute :>> shownByPages = 5;
        attribute :>> shot = "hero";
        attribute :>> livery = "military";
        attribute :>> sourceLayout = "CL-05";
    }
    part blenderCl05Rear : BlenderRender {
        attribute :>> fileName = "CL-05-rear.jpg";
        attribute :>> producer = "tools/cad/blender_render.py";
        attribute :>> shownByPages = 3;
        attribute :>> shot = "rear";
        attribute :>> livery = "industrial";
        attribute :>> sourceLayout = "CL-05";
    }
    part blenderCl05RearMilitary : BlenderRender {
        attribute :>> fileName = "CL-05-rear-military.jpg";
        attribute :>> producer = "tools/cad/blender_render.py";
        attribute :>> shownByPages = 3;
        attribute :>> shot = "rear";
        attribute :>> livery = "military";
        attribute :>> sourceLayout = "CL-05";
    }
    part blenderCl05Kneel : BlenderRender {
        attribute :>> fileName = "CL-05-kneel.jpg";
        attribute :>> producer = "tools/cad/blender_render.py";
        attribute :>> shownByPages = 5;
        attribute :>> shot = "kneel";
        attribute :>> livery = "industrial";
        attribute :>> sourceLayout = "CL-05-kneel";
    }
    part blenderCl05KneelMilitary : BlenderRender {
        attribute :>> fileName = "CL-05-kneel-military.jpg";
        attribute :>> producer = "tools/cad/blender_render.py";
        attribute :>> shownByPages = 4;
        attribute :>> shot = "kneel";
        attribute :>> livery = "military";
        attribute :>> sourceLayout = "CL-05-kneel";
    }
    part blenderCl05Emergency : BlenderRender {
        attribute :>> fileName = "CL-05-emergency.jpg";
        attribute :>> producer = "tools/cad/blender_render.py";
        attribute :>> shownByPages = 4;
        attribute :>> shot = "emergency";
        attribute :>> livery = "industrial";
        attribute :>> sourceLayout = "CL-05-emergency";
    }
    part blenderCl05EmergencyMilitary : BlenderRender {
        attribute :>> fileName = "CL-05-emergency-military.jpg";
        attribute :>> producer = "tools/cad/blender_render.py";
        attribute :>> shownByPages = 3;
        attribute :>> shot = "emergency";
        attribute :>> livery = "military";
        attribute :>> sourceLayout = "CL-05-emergency";
    }
    part blenderCl05Carry : BlenderRender {
        attribute :>> fileName = "CL-05-carry.jpg";
        attribute :>> producer = "tools/cad/blender_render.py";
        attribute :>> shownByPages = 3;
        attribute :>> shot = "carry";
        attribute :>> livery = "industrial";
        attribute :>> sourceLayout = "CL-05-carry";
    }
    part blenderCl05CarryMilitary : BlenderRender {
        attribute :>> fileName = "CL-05-carry-military.jpg";
        attribute :>> producer = "tools/cad/blender_render.py";
        attribute :>> shownByPages = 3;
        attribute :>> shot = "carry";
        attribute :>> livery = "military";
        attribute :>> sourceLayout = "CL-05-carry";
    }
    part clipCl05WalkLoadedMilitaryGif : WalkClip {
        attribute :>> fileName = "CL-05-walk-loaded-military.gif";
        attribute :>> producer = "tools/cad/blender_walk.py";
        attribute :>> shownByPages = 3;
        attribute :>> format = "gif";
    }
    part clipCl05WalkLoadedMilitaryMp4 : WalkClip {
        attribute :>> fileName = "CL-05-walk-loaded-military.mp4";
        attribute :>> producer = "tools/cad/blender_walk.py";
        attribute :>> shownByPages = 3;
        attribute :>> format = "mp4";
    }
    part clipCl05WalkMilitaryGif : WalkClip {
        attribute :>> fileName = "CL-05-walk-military.gif";
        attribute :>> producer = "tools/cad/blender_walk.py";
        attribute :>> shownByPages = 3;
        attribute :>> format = "gif";
    }
    part clipCl05WalkMilitaryMp4 : WalkClip {
        attribute :>> fileName = "CL-05-walk-military.mp4";
        attribute :>> producer = "tools/cad/blender_walk.py";
        attribute :>> shownByPages = 3;
        attribute :>> format = "mp4";
    }
}
