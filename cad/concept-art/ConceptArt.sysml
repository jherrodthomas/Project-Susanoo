// ConceptArt — generated by tools/figures/art_readme.py from cad/concept-art/README.md.
// Do not edit by hand: change the hand-written page or the generator and regenerate.
// Status: AI concept art for communication; not engineering, not evidence.

package ConceptArt {
    private import ScalarValues::*;
    doc /* The AI concept art of CL-05 (cad/concept-art/README.md). */
    part def ConceptArtItem {
        doc /* One AI-generated image or clip made from a project render. Never engineering evidence. */
        attribute fileName : String;
        attribute sourceRender : String;
        attribute jobId : String;
        attribute aiGenerated : Boolean = true;
        attribute engineeringUse : Boolean = false;
    }
    part def ConceptImage :> ConceptArtItem {
        attribute setting : String;
        attribute livery : String;
        attribute closeToCad : Boolean;
        attribute difference : String;
    }
    part def ConceptClip :> ConceptArtItem {
        attribute seconds : Integer;
        attribute endFrame : String [0..1];
    }
    part imageCl05PortDawn : ConceptImage {
        attribute :>> fileName = "CL-05-port-dawn.jpg";
        attribute :>> sourceRender = "CL-05-hero.jpg";
        attribute :>> jobId = "04756f8e";
        attribute :>> setting = "Container port, dawn";
        attribute :>> livery = "industrial";
        attribute :>> closeToCad = false;
        attribute :>> difference = "Drone shown on a side platform at shoulder height instead of the raised rear dock; feet drawn as flat skids";
    }
    part imageCl05LumberYard : ConceptImage {
        attribute :>> fileName = "CL-05-lumber-yard.jpg";
        attribute :>> sourceRender = "CL-05-hero.jpg";
        attribute :>> jobId = "18b97885";
        attribute :>> setting = "Lumber yard, overcast";
        attribute :>> livery = "industrial";
        attribute :>> closeToCad = false;
        attribute :>> difference = "Same drone placement as above";
    }
    part imageCl05KneelNight : ConceptImage {
        attribute :>> fileName = "CL-05-kneel-night.jpg";
        attribute :>> sourceRender = "CL-05-kneel.jpg";
        attribute :>> jobId = "aaf0cb10";
        attribute :>> setting = "Kneel for egress, night rain";
        attribute :>> livery = "industrial";
        attribute :>> closeToCad = true;
        attribute :>> difference = "Close to the CAD";
    }
    part imageCl05KneelMorning : ConceptImage {
        attribute :>> fileName = "CL-05-kneel-morning.jpg";
        attribute :>> sourceRender = "CL-05-kneel.jpg";
        attribute :>> jobId = "f27db76a";
        attribute :>> setting = "Kneel for ingress, morning";
        attribute :>> livery = "industrial";
        attribute :>> closeToCad = false;
        attribute :>> difference = "Stowed claws drawn closer to the opening than the CAD places them";
    }
    part imageCl05EmergencyWarehouse : ConceptImage {
        attribute :>> fileName = "CL-05-emergency-warehouse.jpg";
        attribute :>> sourceRender = "CL-05-emergency.jpg";
        attribute :>> jobId = "3ec32fc5";
        attribute :>> setting = "Emergency exit drill, warehouse";
        attribute :>> livery = "industrial";
        attribute :>> closeToCad = false;
        attribute :>> difference = "The rope ladder hangs flat against the hull over the safety box and leg instead of from the swing-out davit 0.60 m out: the snag the davit exists to avoid";
    }
    part imageCl05EmergencyTraining : ConceptImage {
        attribute :>> fileName = "CL-05-emergency-training.jpg";
        attribute :>> sourceRender = "CL-05-emergency.jpg";
        attribute :>> jobId = "ec01b505";
        attribute :>> setting = "Emergency egress training, dusk";
        attribute :>> livery = "industrial";
        attribute :>> closeToCad = false;
        attribute :>> difference = "The pilot wears a fall-arrest harness: a candidate control for the fall-from-height hazard of emergency egress, suggested by the image, to be evaluated, not evi";
    }
    part imageCl05MilitaryLogistics : ConceptImage {
        attribute :>> fileName = "CL-05-military-logistics.jpg";
        attribute :>> sourceRender = "CL-05-hero-military.jpg";
        attribute :>> jobId = "f82bd302";
        attribute :>> setting = "Forward logistics base";
        attribute :>> livery = "military";
        attribute :>> closeToCad = false;
        attribute :>> difference = "Carries a pallet in its claws while walking: allowed only under the loaded-walking conditions the lead set (2026-11-12: carry pose, secured load, mass and speed";
    }
    part imageCl05MilitaryEngineering : ConceptImage {
        attribute :>> fileName = "CL-05-military-engineering.jpg";
        attribute :>> sourceRender = "CL-05-hero-military.jpg";
        attribute :>> jobId = "11068be0";
        attribute :>> setting = "Disaster engineering";
        attribute :>> livery = "military";
        attribute :>> closeToCad = false;
        attribute :>> difference = "Rescue crew shown inside the arm’s reach: the arms’ strike and pinch zone. A scene to prevent, not a procedure";
    }
    part imageCl05MilitaryMaintenance : ConceptImage {
        attribute :>> fileName = "CL-05-military-maintenance.jpg";
        attribute :>> sourceRender = "CL-05-kneel-military.jpg";
        attribute :>> jobId = "79b790c8";
        attribute :>> setting = "Field maintenance, dusk";
        attribute :>> livery = "military";
        attribute :>> closeToCad = true;
        attribute :>> difference = "Close to the CAD";
    }
    part imageCl05MilitaryRelief : ConceptImage {
        attribute :>> fileName = "CL-05-military-relief.jpg";
        attribute :>> sourceRender = "CL-05-kneel-military.jpg";
        attribute :>> jobId = "c0cf31bc";
        attribute :>> setting = "Winter disaster relief";
        attribute :>> livery = "military";
        attribute :>> closeToCad = false;
        attribute :>> difference = "The red internal release handle reads as a small red cross. The Red Cross emblem is legally protected; the design should keep that handle unmistakably a handle";
    }
    part clipCl05KneelClip : ConceptClip {
        attribute :>> fileName = "CL-05-kneel-clip.mp4";
        attribute :>> sourceRender = "CL-05-hero.jpg";
        attribute :>> jobId = "8413db6a";
        attribute :>> seconds = 8;
        attribute :>> endFrame = "CL-05-kneel.jpg";
    }
    part clipCl05MilitaryWalkClip : ConceptClip {
        attribute :>> fileName = "CL-05-military-walk-clip.mp4";
        attribute :>> sourceRender = "CL-05-hero-military.jpg";
        attribute :>> jobId = "71699eae";
        attribute :>> seconds = 8;
    }
}
