// Toolchain — generated by tools/figures/tools_readme.py from .github/workflows/docs-check.yml.
// Do not edit by hand: change the workflow or the generator and regenerate.
// Status: what CI runs; passing it is not a review.

package Toolchain {
    doc /* The documentation check as run by CI (tools/README.md). */
    action def DocsCheck {
        doc /* The docs-check workflow, job readme-figures: its steps in order (generated from the workflow). */
        action checkReadmesRegenerateEveryFigureAndSysm { doc /* Check READMEs, regenerate every figure and SysML view, and diff */ }
        action analysisWorksheetsImagesCsvExcelWorkbook { doc /* Analysis worksheets match the records */ }
        action frontPageReadmeFiguresAndNumbersMatchThe { doc /* Front-page README figures and numbers match the records */ }
        action recordFiguresAreCurrentDecisionsTraceabi { doc /* Record figures are current */ }
        action everyFolderHasAVisualPreviewDocsPreviews { doc /* Every folder has a visual preview */ }
        action previewTests { doc /* Preview tests */ }
        action systemVCyclePageWikiPageAndStillAreCurre { doc /* System V cycle page, wiki page and still are current */ }
        action systemVCycleTests { doc /* System V cycle tests */ }
        action reliabilityPilotPageFiguresAndNumbersAre { doc /* Reliability pilot page, figures and numbers are current */ }
        action reliabilityTests { doc /* Reliability tests */ }
        action wikiCopiesOfTheRepositoryPagesAreCurrent { doc /* Wiki copies of the repository pages are current */ }
        action everyPageAndFigureExplainsItsAbbreviatio { doc /* Every page and figure explains its abbreviations and codes */ }
        action termsTests { doc /* Terms tests */ }
        first start then checkReadmesRegenerateEveryFigureAndSysm;
        first checkReadmesRegenerateEveryFigureAndSysm then analysisWorksheetsImagesCsvExcelWorkbook;
        first analysisWorksheetsImagesCsvExcelWorkbook then frontPageReadmeFiguresAndNumbersMatchThe;
        first frontPageReadmeFiguresAndNumbersMatchThe then recordFiguresAreCurrentDecisionsTraceabi;
        first recordFiguresAreCurrentDecisionsTraceabi then everyFolderHasAVisualPreviewDocsPreviews;
        first everyFolderHasAVisualPreviewDocsPreviews then previewTests;
        first previewTests then systemVCyclePageWikiPageAndStillAreCurre;
        first systemVCyclePageWikiPageAndStillAreCurre then systemVCycleTests;
        first systemVCycleTests then reliabilityPilotPageFiguresAndNumbersAre;
        first reliabilityPilotPageFiguresAndNumbersAre then reliabilityTests;
        first reliabilityTests then wikiCopiesOfTheRepositoryPagesAreCurrent;
        first wikiCopiesOfTheRepositoryPagesAreCurrent then everyPageAndFigureExplainsItsAbbreviatio;
        first everyPageAndFigureExplainsItsAbbreviatio then termsTests;
        first termsTests then done;
    }
}
